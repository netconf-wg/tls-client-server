module iana-tls-cipher-suite-algs {
  yang-version 1.1;
  namespace "urn:ietf:params:xml:ns:yang:iana-tls-cipher-suite-algs";
  prefix tlscsa;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines enumerations for the Cipher Suite
     algorithms defined in the 'TLS Cipher Suites' sub-registry
     of the 'Transport Layer Security (TLS) Parameters' registry
     maintained by IANA.

     Copyright (c) 2024 IETF Trust and the persons identified as
     authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC FFFF
     (https://www.rfc-editor.org/info/rfcFFFF); see the RFC
     itself for full legal notices.

     All versions of this module are published by IANA at
     https://www.iana.org/assignments/yang-parameters.";

  revision 2024-03-02 {
    description
      "This initial version of the module was created using
       the script defined in RFC FFFF to reflect the contents
       of the cipher-suite algorithms registry maintained by IANA.";
    reference
      "RFC FFFF: YANG Groupings for TLS Clients and TLS Servers";
  }

  typedef tls-cipher-suite-algorithm {
    type enumeration {
      enum TLS_NULL_WITH_NULL_NULL {
        status deprecated;
        description
          "Enumeration for the 'TLS_NULL_WITH_NULL_NULL' algorithm.";
        reference
          "RFC 5246:
             The Transport Layer Security (TLS) Protocol Version
             1.2";
      }
      enum TLS_RSA_WITH_NULL_MD5 {
        status deprecated;
        description
          "Enumeration for the 'TLS_RSA_WITH_NULL_MD5' algorithm.";
        reference
          "RFC 5246:
             The Transport Layer Security (TLS) Protocol Version
             1.2";
      }
      enum TLS_RSA_WITH_NULL_SHA {
        status deprecated;
        description
          "Enumeration for the 'TLS_RSA_WITH_NULL_SHA' algorithm.";
        reference
          "RFC 5246:
             The Transport Layer Security (TLS) Protocol Version
             1.2";
      }
      enum TLS_RSA_EXPORT_WITH_RC4_40_MD5 {
        status deprecated;
        description
          "Enumeration for the 'TLS_RSA_EXPORT_WITH_RC4_40_MD5'
           algorithm.";
        reference
          "RFC 4346:
             The Transport Layer Security (TLS) Protocol Version 1.1
           RFC 6347:
             Datagram Transport Layer Security Version 1.2";
      }
      enum TLS_RSA_WITH_RC4_128_MD5 {
        status deprecated;
        description
          "Enumeration for the 'TLS_RSA_WITH_RC4_128_MD5'
           algorithm.";
        reference
          "RFC 5246:
             The Transport Layer Security (TLS) Protocol Version 1.2
           RFC 6347:
             Datagram Transport Layer Security Version 1.2";
      }
      enum TLS_RSA_WITH_RC4_128_SHA {
        status deprecated;
        description
          "Enumeration for the 'TLS_RSA_WITH_RC4_128_SHA'
           algorithm.";
        reference
          "RFC 5246:
             The Transport Layer Security (TLS) Protocol Version 1.2
           RFC 6347:
             Datagram Transport Layer Security Version 1.2";
      }
      enum TLS_RSA_EXPORT_WITH_RC2_CBC_40_MD5 {
        status deprecated;
        description
          "Enumeration for the 'TLS_RSA_EXPORT_WITH_RC2_CBC_40_MD5'
           algorithm.";
        reference
          "RFC 4346:
             The Transport Layer Security (TLS) Protocol Version
             1.1";
      }
      enum TLS_RSA_WITH_IDEA_CBC_SHA {
        status deprecated;
        description
          "Enumeration for the 'TLS_RSA_WITH_IDEA_CBC_SHA'
           algorithm.";
        reference
          "RFC 8996:
             Deprecating TLS 1.0 and TLS 1.1";
      }
      enum TLS_RSA_EXPORT_WITH_DES40_CBC_SHA {
        status deprecated;
        description
          "Enumeration for the 'TLS_RSA_EXPORT_WITH_DES40_CBC_SHA'
           algorithm.";
        reference
          "RFC 4346:
             The Transport Layer Security (TLS) Protocol Version
             1.1";
      }
      enum TLS_RSA_WITH_DES_CBC_SHA {
        status deprecated;
        description
          "Enumeration for the 'TLS_RSA_WITH_DES_CBC_SHA'
           algorithm.";
        reference
          "RFC 8996:
             Deprecating TLS 1.0 and TLS 1.1";
      }
      enum TLS_RSA_WITH_3DES_EDE_CBC_SHA {
        status deprecated;
        description
          "Enumeration for the 'TLS_RSA_WITH_3DES_EDE_CBC_SHA'
           algorithm.";
        reference
          "RFC 5246:
             The Transport Layer Security (TLS) Protocol Version
             1.2";
      }
      enum TLS_DH_DSS_EXPORT_WITH_DES40_CBC_SHA {
        status deprecated;
        description
          "Enumeration for the 'TLS_DH_DSS_EXPORT_WITH_DES40_CBC_SHA'
           algorithm.";
        reference
          "RFC 4346:
             The Transport Layer Security (TLS) Protocol Version
             1.1";
      }
      enum TLS_DH_DSS_WITH_DES_CBC_SHA {
        status deprecated;
        description
          "Enumeration for the 'TLS_DH_DSS_WITH_DES_CBC_SHA'
           algorithm.";
        reference
          "RFC 8996:
             Deprecating TLS 1.0 and TLS 1.1";
      }
      enum TLS_DH_DSS_WITH_3DES_EDE_CBC_SHA {
        status deprecated;
        description
          "Enumeration for the 'TLS_DH_DSS_WITH_3DES_EDE_CBC_SHA'
           algorithm.";
        reference
          "RFC 5246:
             The Transport Layer Security (TLS) Protocol Version
             1.2";
      }
      enum TLS_DH_RSA_EXPORT_WITH_DES40_CBC_SHA {
        status deprecated;
        description
          "Enumeration for the 'TLS_DH_RSA_EXPORT_WITH_DES40_CBC_SHA'
           algorithm.";
        reference
          "RFC 4346:
             The Transport Layer Security (TLS) Protocol Version
             1.1";
      }
      enum TLS_DH_RSA_WITH_DES_CBC_SHA {
        status deprecated;
        description
          "Enumeration for the 'TLS_DH_RSA_WITH_DES_CBC_SHA'
           algorithm.";
        reference
          "RFC 8996:
             Deprecating TLS 1.0 and TLS 1.1";
      }
      enum TLS_DH_RSA_WITH_3DES_EDE_CBC_SHA {
        status deprecated;
        description
          "Enumeration for the 'TLS_DH_RSA_WITH_3DES_EDE_CBC_SHA'
           algorithm.";
        reference
          "RFC 5246:
             The Transport Layer Security (TLS) Protocol Version
             1.2";
      }
      enum TLS_DHE_DSS_EXPORT_WITH_DES40_CBC_SHA {
        status deprecated;
        description
          "Enumeration for the
           'TLS_DHE_DSS_EXPORT_WITH_DES40_CBC_SHA' algorithm.";
        reference
          "RFC 4346:
             The Transport Layer Security (TLS) Protocol Version
             1.1";
      }
      enum TLS_DHE_DSS_WITH_DES_CBC_SHA {
        status deprecated;
        description
          "Enumeration for the 'TLS_DHE_DSS_WITH_DES_CBC_SHA'
           algorithm.";
        reference
          "RFC 8996:
             Deprecating TLS 1.0 and TLS 1.1";
      }
      enum TLS_DHE_DSS_WITH_3DES_EDE_CBC_SHA {
        status deprecated;
        description
          "Enumeration for the 'TLS_DHE_DSS_WITH_3DES_EDE_CBC_SHA'
           algorithm.";
        reference
          "RFC 5246:
             The Transport Layer Security (TLS) Protocol Version
             1.2";
      }
      enum TLS_DHE_RSA_EXPORT_WITH_DES40_CBC_SHA {
        status deprecated;
        description
          "Enumeration for the
           'TLS_DHE_RSA_EXPORT_WITH_DES40_CBC_SHA' algorithm.";
        reference
          "RFC 4346:
             The Transport Layer Security (TLS) Protocol Version
             1.1";
      }
      enum TLS_DHE_RSA_WITH_DES_CBC_SHA {
        status deprecated;
        description
          "Enumeration for the 'TLS_DHE_RSA_WITH_DES_CBC_SHA'
           algorithm.";
        reference
          "RFC 8996:
             Deprecating TLS 1.0 and TLS 1.1";
      }
      enum TLS_DHE_RSA_WITH_3DES_EDE_CBC_SHA {
        status deprecated;
        description
          "Enumeration for the 'TLS_DHE_RSA_WITH_3DES_EDE_CBC_SHA'
           algorithm.";
        reference
          "RFC 5246:
             The Transport Layer Security (TLS) Protocol Version
             1.2";
      }
      enum TLS_DH_anon_EXPORT_WITH_RC4_40_MD5 {
        status deprecated;
        description
          "Enumeration for the 'TLS_DH_anon_EXPORT_WITH_RC4_40_MD5'
           algorithm.";
        reference
          "RFC 4346:
             The Transport Layer Security (TLS) Protocol Version 1.1
           RFC 6347:
             Datagram Transport Layer Security Version 1.2";
      }
      enum TLS_DH_anon_WITH_RC4_128_MD5 {
        status deprecated;
        description
          "Enumeration for the 'TLS_DH_anon_WITH_RC4_128_MD5'
           algorithm.";
        reference
          "RFC 5246:
             The Transport Layer Security (TLS) Protocol Version 1.2
           RFC 6347:
             Datagram Transport Layer Security Version 1.2";
      }
      enum TLS_DH_anon_EXPORT_WITH_DES40_CBC_SHA {
        status deprecated;
        description
          "Enumeration for the
           'TLS_DH_anon_EXPORT_WITH_DES40_CBC_SHA' algorithm.";
        reference
          "RFC 4346:
             The Transport Layer Security (TLS) Protocol Version
             1.1";
      }
      enum TLS_DH_anon_WITH_DES_CBC_SHA {
        status deprecated;
        description
          "Enumeration for the 'TLS_DH_anon_WITH_DES_CBC_SHA'
           algorithm.";
        reference
          "RFC 8996:
             Deprecating TLS 1.0 and TLS 1.1";
      }
      enum TLS_DH_anon_WITH_3DES_EDE_CBC_SHA {
        status deprecated;
        description
          "Enumeration for the 'TLS_DH_anon_WITH_3DES_EDE_CBC_SHA'
           algorithm.";
        reference
          "RFC 5246:
             The Transport Layer Security (TLS) Protocol Version
             1.2";
      }
      enum TLS_KRB5_WITH_DES_CBC_SHA {
        status deprecated;
        description
          "Enumeration for the 'TLS_KRB5_WITH_DES_CBC_SHA'
           algorithm.";
        reference
          "RFC 2712:
             Addition of Kerberos Cipher Suites to Transport Layer
             Security (TLS)";
      }
      enum TLS_KRB5_WITH_3DES_EDE_CBC_SHA {
        status deprecated;
        description
          "Enumeration for the 'TLS_KRB5_WITH_3DES_EDE_CBC_SHA'
           algorithm.";
        reference
          "RFC 2712:
             Addition of Kerberos Cipher Suites to Transport Layer
             Security (TLS)";
      }
      enum TLS_KRB5_WITH_RC4_128_SHA {
        status deprecated;
        description
          "Enumeration for the 'TLS_KRB5_WITH_RC4_128_SHA'
           algorithm.";
        reference
          "RFC 2712:
             Addition of Kerberos Cipher Suites to Transport Layer
             Security (TLS)
           RFC 6347:
             Datagram Transport Layer Security Version 1.2";
      }
      enum TLS_KRB5_WITH_IDEA_CBC_SHA {
        status deprecated;
        description
          "Enumeration for the 'TLS_KRB5_WITH_IDEA_CBC_SHA'
           algorithm.";
        reference
          "RFC 2712:
             Addition of Kerberos Cipher Suites to Transport Layer
             Security (TLS)";
      }
      enum TLS_KRB5_WITH_DES_CBC_MD5 {
        status deprecated;
        description
          "Enumeration for the 'TLS_KRB5_WITH_DES_CBC_MD5'
           algorithm.";
        reference
          "RFC 2712:
             Addition of Kerberos Cipher Suites to Transport Layer
             Security (TLS)";
      }
      enum TLS_KRB5_WITH_3DES_EDE_CBC_MD5 {
        status deprecated;
        description
          "Enumeration for the 'TLS_KRB5_WITH_3DES_EDE_CBC_MD5'
           algorithm.";
        reference
          "RFC 2712:
             Addition of Kerberos Cipher Suites to Transport Layer
             Security (TLS)";
      }
      enum TLS_KRB5_WITH_RC4_128_MD5 {
        status deprecated;
        description
          "Enumeration for the 'TLS_KRB5_WITH_RC4_128_MD5'
           algorithm.";
        reference
          "RFC 2712:
             Addition of Kerberos Cipher Suites to Transport Layer
             Security (TLS)
           RFC 6347:
             Datagram Transport Layer Security Version 1.2";
      }
      enum TLS_KRB5_WITH_IDEA_CBC_MD5 {
        status deprecated;
        description
          "Enumeration for the 'TLS_KRB5_WITH_IDEA_CBC_MD5'
           algorithm.";
        reference
          "RFC 2712:
             Addition of Kerberos Cipher Suites to Transport Layer
             Security (TLS)";
      }
      enum TLS_KRB5_EXPORT_WITH_DES_CBC_40_SHA {
        status deprecated;
        description
          "Enumeration for the 'TLS_KRB5_EXPORT_WITH_DES_CBC_40_SHA'
           algorithm.";
        reference
          "RFC 2712:
             Addition of Kerberos Cipher Suites to Transport Layer
             Security (TLS)";
      }
      enum TLS_KRB5_EXPORT_WITH_RC2_CBC_40_SHA {
        status deprecated;
        description
          "Enumeration for the 'TLS_KRB5_EXPORT_WITH_RC2_CBC_40_SHA'
           algorithm.";
        reference
          "RFC 2712:
             Addition of Kerberos Cipher Suites to Transport Layer
             Security (TLS)";
      }
      enum TLS_KRB5_EXPORT_WITH_RC4_40_SHA {
        status deprecated;
        description
          "Enumeration for the 'TLS_KRB5_EXPORT_WITH_RC4_40_SHA'
           algorithm.";
        reference
          "RFC 2712:
             Addition of Kerberos Cipher Suites to Transport Layer
             Security (TLS)
           RFC 6347:
             Datagram Transport Layer Security Version 1.2";
      }
      enum TLS_KRB5_EXPORT_WITH_DES_CBC_40_MD5 {
        status deprecated;
        description
          "Enumeration for the 'TLS_KRB5_EXPORT_WITH_DES_CBC_40_MD5'
           algorithm.";
        reference
          "RFC 2712:
             Addition of Kerberos Cipher Suites to Transport Layer
             Security (TLS)";
      }
      enum TLS_KRB5_EXPORT_WITH_RC2_CBC_40_MD5 {
        status deprecated;
        description
          "Enumeration for the 'TLS_KRB5_EXPORT_WITH_RC2_CBC_40_MD5'
           algorithm.";
        reference
          "RFC 2712:
             Addition of Kerberos Cipher Suites to Transport Layer
             Security (TLS)";
      }
      enum TLS_KRB5_EXPORT_WITH_RC4_40_MD5 {
        status deprecated;
        description
          "Enumeration for the 'TLS_KRB5_EXPORT_WITH_RC4_40_MD5'
           algorithm.";
        reference
          "RFC 2712:
             Addition of Kerberos Cipher Suites to Transport Layer
             Security (TLS)
           RFC 6347:
             Datagram Transport Layer Security Version 1.2";
      }
      enum TLS_PSK_WITH_NULL_SHA {
        status deprecated;
        description
          "Enumeration for the 'TLS_PSK_WITH_NULL_SHA' algorithm.";
        reference
          "RFC 4785:
             Pre-Shared Key (PSK) Ciphersuites with NULL Encryption
             for Transport Layer Security (TLS)";
      }
      enum TLS_DHE_PSK_WITH_NULL_SHA {
        status deprecated;
        description
          "Enumeration for the 'TLS_DHE_PSK_WITH_NULL_SHA'
           algorithm.";
        reference
          "RFC 4785:
             Pre-Shared Key (PSK) Ciphersuites with NULL Encryption
             for Transport Layer Security (TLS)";
      }
      enum TLS_RSA_PSK_WITH_NULL_SHA {
        status deprecated;
        description
          "Enumeration for the 'TLS_RSA_PSK_WITH_NULL_SHA'
           algorithm.";
        reference
          "RFC 4785:
             Pre-Shared Key (PSK) Ciphersuites with NULL Encryption
             for Transport Layer Security (TLS)";
      }
      enum TLS_RSA_WITH_AES_128_CBC_SHA {
        status deprecated;
        description
          "Enumeration for the 'TLS_RSA_WITH_AES_128_CBC_SHA'
           algorithm.";
        reference
          "RFC 5246:
             The Transport Layer Security (TLS) Protocol Version
             1.2";
      }
      enum TLS_DH_DSS_WITH_AES_128_CBC_SHA {
        status deprecated;
        description
          "Enumeration for the 'TLS_DH_DSS_WITH_AES_128_CBC_SHA'
           algorithm.";
        reference
          "RFC 5246:
             The Transport Layer Security (TLS) Protocol Version
             1.2";
      }
      enum TLS_DH_RSA_WITH_AES_128_CBC_SHA {
        status deprecated;
        description
          "Enumeration for the 'TLS_DH_RSA_WITH_AES_128_CBC_SHA'
           algorithm.";
        reference
          "RFC 5246:
             The Transport Layer Security (TLS) Protocol Version
             1.2";
      }
      enum TLS_DHE_DSS_WITH_AES_128_CBC_SHA {
        status deprecated;
        description
          "Enumeration for the 'TLS_DHE_DSS_WITH_AES_128_CBC_SHA'
           algorithm.";
        reference
          "RFC 5246:
             The Transport Layer Security (TLS) Protocol Version
             1.2";
      }
      enum TLS_DHE_RSA_WITH_AES_128_CBC_SHA {
        status deprecated;
        description
          "Enumeration for the 'TLS_DHE_RSA_WITH_AES_128_CBC_SHA'
           algorithm.";
        reference
          "RFC 5246:
             The Transport Layer Security (TLS) Protocol Version
             1.2";
      }
      enum TLS_DH_anon_WITH_AES_128_CBC_SHA {
        status deprecated;
        description
          "Enumeration for the 'TLS_DH_anon_WITH_AES_128_CBC_SHA'
           algorithm.";
        reference
          "RFC 5246:
             The Transport Layer Security (TLS) Protocol Version
             1.2";
      }
      enum TLS_RSA_WITH_AES_256_CBC_SHA {
        status deprecated;
        description
          "Enumeration for the 'TLS_RSA_WITH_AES_256_CBC_SHA'
           algorithm.";
        reference
          "RFC 5246:
             The Transport Layer Security (TLS) Protocol Version
             1.2";
      }
      enum TLS_DH_DSS_WITH_AES_256_CBC_SHA {
        status deprecated;
        description
          "Enumeration for the 'TLS_DH_DSS_WITH_AES_256_CBC_SHA'
           algorithm.";
        reference
          "RFC 5246:
             The Transport Layer Security (TLS) Protocol Version
             1.2";
      }
      enum TLS_DH_RSA_WITH_AES_256_CBC_SHA {
        status deprecated;
        description
          "Enumeration for the 'TLS_DH_RSA_WITH_AES_256_CBC_SHA'
           algorithm.";
        reference
          "RFC 5246:
             The Transport Layer Security (TLS) Protocol Version
             1.2";
      }
      enum TLS_DHE_DSS_WITH_AES_256_CBC_SHA {
        status deprecated;
        description
          "Enumeration for the 'TLS_DHE_DSS_WITH_AES_256_CBC_SHA'
           algorithm.";
        reference
          "RFC 5246:
             The Transport Layer Security (TLS) Protocol Version
             1.2";
      }
      enum TLS_DHE_RSA_WITH_AES_256_CBC_SHA {
        status deprecated;
        description
          "Enumeration for the 'TLS_DHE_RSA_WITH_AES_256_CBC_SHA'
           algorithm.";
        reference
          "RFC 5246:
             The Transport Layer Security (TLS) Protocol Version
             1.2";
      }
      enum TLS_DH_anon_WITH_AES_256_CBC_SHA {
        status deprecated;
        description
          "Enumeration for the 'TLS_DH_anon_WITH_AES_256_CBC_SHA'
           algorithm.";
        reference
          "RFC 5246:
             The Transport Layer Security (TLS) Protocol Version
             1.2";
      }
      enum TLS_RSA_WITH_NULL_SHA256 {
        status deprecated;
        description
          "Enumeration for the 'TLS_RSA_WITH_NULL_SHA256'
           algorithm.";
        reference
          "RFC 5246:
             The Transport Layer Security (TLS) Protocol Version
             1.2";
      }
      enum TLS_RSA_WITH_AES_128_CBC_SHA256 {
        status deprecated;
        description
          "Enumeration for the 'TLS_RSA_WITH_AES_128_CBC_SHA256'
           algorithm.";
        reference
          "RFC 5246:
             The Transport Layer Security (TLS) Protocol Version
             1.2";
      }
      enum TLS_RSA_WITH_AES_256_CBC_SHA256 {
        status deprecated;
        description
          "Enumeration for the 'TLS_RSA_WITH_AES_256_CBC_SHA256'
           algorithm.";
        reference
          "RFC 5246:
             The Transport Layer Security (TLS) Protocol Version
             1.2";
      }
      enum TLS_DH_DSS_WITH_AES_128_CBC_SHA256 {
        status deprecated;
        description
          "Enumeration for the 'TLS_DH_DSS_WITH_AES_128_CBC_SHA256'
           algorithm.";
        reference
          "RFC 5246:
             The Transport Layer Security (TLS) Protocol Version
             1.2";
      }
      enum TLS_DH_RSA_WITH_AES_128_CBC_SHA256 {
        status deprecated;
        description
          "Enumeration for the 'TLS_DH_RSA_WITH_AES_128_CBC_SHA256'
           algorithm.";
        reference
          "RFC 5246:
             The Transport Layer Security (TLS) Protocol Version
             1.2";
      }
      enum TLS_DHE_DSS_WITH_AES_128_CBC_SHA256 {
        status deprecated;
        description
          "Enumeration for the 'TLS_DHE_DSS_WITH_AES_128_CBC_SHA256'
           algorithm.";
        reference
          "RFC 5246:
             The Transport Layer Security (TLS) Protocol Version
             1.2";
      }
      enum TLS_RSA_WITH_CAMELLIA_128_CBC_SHA {
        status deprecated;
        description
          "Enumeration for the 'TLS_RSA_WITH_CAMELLIA_128_CBC_SHA'
           algorithm.";
        reference
          "RFC 5932:
             Camellia Cipher Suites for TLS";
      }
      enum TLS_DH_DSS_WITH_CAMELLIA_128_CBC_SHA {
        status deprecated;
        description
          "Enumeration for the 'TLS_DH_DSS_WITH_CAMELLIA_128_CBC_SHA'
           algorithm.";
        reference
          "RFC 5932:
             Camellia Cipher Suites for TLS";
      }
      enum TLS_DH_RSA_WITH_CAMELLIA_128_CBC_SHA {
        status deprecated;
        description
          "Enumeration for the 'TLS_DH_RSA_WITH_CAMELLIA_128_CBC_SHA'
           algorithm.";
        reference
          "RFC 5932:
             Camellia Cipher Suites for TLS";
      }
      enum TLS_DHE_DSS_WITH_CAMELLIA_128_CBC_SHA {
        status deprecated;
        description
          "Enumeration for the
           'TLS_DHE_DSS_WITH_CAMELLIA_128_CBC_SHA' algorithm.";
        reference
          "RFC 5932:
             Camellia Cipher Suites for TLS";
      }
      enum TLS_DHE_RSA_WITH_CAMELLIA_128_CBC_SHA {
        status deprecated;
        description
          "Enumeration for the
           'TLS_DHE_RSA_WITH_CAMELLIA_128_CBC_SHA' algorithm.";
        reference
          "RFC 5932:
             Camellia Cipher Suites for TLS";
      }
      enum TLS_DH_anon_WITH_CAMELLIA_128_CBC_SHA {
        status deprecated;
        description
          "Enumeration for the
           'TLS_DH_anon_WITH_CAMELLIA_128_CBC_SHA' algorithm.";
        reference
          "RFC 5932:
             Camellia Cipher Suites for TLS";
      }
      enum TLS_DHE_RSA_WITH_AES_128_CBC_SHA256 {
        status deprecated;
        description
          "Enumeration for the 'TLS_DHE_RSA_WITH_AES_128_CBC_SHA256'
           algorithm.";
        reference
          "RFC 5246:
             The Transport Layer Security (TLS) Protocol Version
             1.2";
      }
      enum TLS_DH_DSS_WITH_AES_256_CBC_SHA256 {
        status deprecated;
        description
          "Enumeration for the 'TLS_DH_DSS_WITH_AES_256_CBC_SHA256'
           algorithm.";
        reference
          "RFC 5246:
             The Transport Layer Security (TLS) Protocol Version
             1.2";
      }
      enum TLS_DH_RSA_WITH_AES_256_CBC_SHA256 {
        status deprecated;
        description
          "Enumeration for the 'TLS_DH_RSA_WITH_AES_256_CBC_SHA256'
           algorithm.";
        reference
          "RFC 5246:
             The Transport Layer Security (TLS) Protocol Version
             1.2";
      }
      enum TLS_DHE_DSS_WITH_AES_256_CBC_SHA256 {
        status deprecated;
        description
          "Enumeration for the 'TLS_DHE_DSS_WITH_AES_256_CBC_SHA256'
           algorithm.";
        reference
          "RFC 5246:
             The Transport Layer Security (TLS) Protocol Version
             1.2";
      }
      enum TLS_DHE_RSA_WITH_AES_256_CBC_SHA256 {
        status deprecated;
        description
          "Enumeration for the 'TLS_DHE_RSA_WITH_AES_256_CBC_SHA256'
           algorithm.";
        reference
          "RFC 5246:
             The Transport Layer Security (TLS) Protocol Version
             1.2";
      }
      enum TLS_DH_anon_WITH_AES_128_CBC_SHA256 {
        status deprecated;
        description
          "Enumeration for the 'TLS_DH_anon_WITH_AES_128_CBC_SHA256'
           algorithm.";
        reference
          "RFC 5246:
             The Transport Layer Security (TLS) Protocol Version
             1.2";
      }
      enum TLS_DH_anon_WITH_AES_256_CBC_SHA256 {
        status deprecated;
        description
          "Enumeration for the 'TLS_DH_anon_WITH_AES_256_CBC_SHA256'
           algorithm.";
        reference
          "RFC 5246:
             The Transport Layer Security (TLS) Protocol Version
             1.2";
      }
      enum TLS_RSA_WITH_CAMELLIA_256_CBC_SHA {
        status deprecated;
        description
          "Enumeration for the 'TLS_RSA_WITH_CAMELLIA_256_CBC_SHA'
           algorithm.";
        reference
          "RFC 5932:
             Camellia Cipher Suites for TLS";
      }
      enum TLS_DH_DSS_WITH_CAMELLIA_256_CBC_SHA {
        status deprecated;
        description
          "Enumeration for the 'TLS_DH_DSS_WITH_CAMELLIA_256_CBC_SHA'
           algorithm.";
        reference
          "RFC 5932:
             Camellia Cipher Suites for TLS";
      }
      enum TLS_DH_RSA_WITH_CAMELLIA_256_CBC_SHA {
        status deprecated;
        description
          "Enumeration for the 'TLS_DH_RSA_WITH_CAMELLIA_256_CBC_SHA'
           algorithm.";
        reference
          "RFC 5932:
             Camellia Cipher Suites for TLS";
      }
      enum TLS_DHE_DSS_WITH_CAMELLIA_256_CBC_SHA {
        status deprecated;
        description
          "Enumeration for the
           'TLS_DHE_DSS_WITH_CAMELLIA_256_CBC_SHA' algorithm.";
        reference
          "RFC 5932:
             Camellia Cipher Suites for TLS";
      }
      enum TLS_DHE_RSA_WITH_CAMELLIA_256_CBC_SHA {
        status deprecated;
        description
          "Enumeration for the
           'TLS_DHE_RSA_WITH_CAMELLIA_256_CBC_SHA' algorithm.";
        reference
          "RFC 5932:
             Camellia Cipher Suites for TLS";
      }
      enum TLS_DH_anon_WITH_CAMELLIA_256_CBC_SHA {
        status deprecated;
        description
          "Enumeration for the
           'TLS_DH_anon_WITH_CAMELLIA_256_CBC_SHA' algorithm.";
        reference
          "RFC 5932:
             Camellia Cipher Suites for TLS";
      }
      enum TLS_PSK_WITH_RC4_128_SHA {
        status deprecated;
        description
          "Enumeration for the 'TLS_PSK_WITH_RC4_128_SHA'
           algorithm.";
        reference
          "RFC 4279:
             Pre-Shared Key Ciphersuites for Transport Layer Security
             (TLS)
           RFC 6347:
             Datagram Transport Layer Security Version 1.2";
      }
      enum TLS_PSK_WITH_3DES_EDE_CBC_SHA {
        status deprecated;
        description
          "Enumeration for the 'TLS_PSK_WITH_3DES_EDE_CBC_SHA'
           algorithm.";
        reference
          "RFC 4279:
             Pre-Shared Key Ciphersuites for Transport Layer Security
             (TLS)";
      }
      enum TLS_PSK_WITH_AES_128_CBC_SHA {
        status deprecated;
        description
          "Enumeration for the 'TLS_PSK_WITH_AES_128_CBC_SHA'
           algorithm.";
        reference
          "RFC 4279:
             Pre-Shared Key Ciphersuites for Transport Layer Security
             (TLS)";
      }
      enum TLS_PSK_WITH_AES_256_CBC_SHA {
        status deprecated;
        description
          "Enumeration for the 'TLS_PSK_WITH_AES_256_CBC_SHA'
           algorithm.";
        reference
          "RFC 4279:
             Pre-Shared Key Ciphersuites for Transport Layer Security
             (TLS)";
      }
      enum TLS_DHE_PSK_WITH_RC4_128_SHA {
        status deprecated;
        description
          "Enumeration for the 'TLS_DHE_PSK_WITH_RC4_128_SHA'
           algorithm.";
        reference
          "RFC 4279:
             Pre-Shared Key Ciphersuites for Transport Layer Security
             (TLS)
           RFC 6347:
             Datagram Transport Layer Security Version 1.2";
      }
      enum TLS_DHE_PSK_WITH_3DES_EDE_CBC_SHA {
        status deprecated;
        description
          "Enumeration for the 'TLS_DHE_PSK_WITH_3DES_EDE_CBC_SHA'
           algorithm.";
        reference
          "RFC 4279:
             Pre-Shared Key Ciphersuites for Transport Layer Security
             (TLS)";
      }
      enum TLS_DHE_PSK_WITH_AES_128_CBC_SHA {
        status deprecated;
        description
          "Enumeration for the 'TLS_DHE_PSK_WITH_AES_128_CBC_SHA'
           algorithm.";
        reference
          "RFC 4279:
             Pre-Shared Key Ciphersuites for Transport Layer Security
             (TLS)";
      }
      enum TLS_DHE_PSK_WITH_AES_256_CBC_SHA {
        status deprecated;
        description
          "Enumeration for the 'TLS_DHE_PSK_WITH_AES_256_CBC_SHA'
           algorithm.";
        reference
          "RFC 4279:
             Pre-Shared Key Ciphersuites for Transport Layer Security
             (TLS)";
      }
      enum TLS_RSA_PSK_WITH_RC4_128_SHA {
        status deprecated;
        description
          "Enumeration for the 'TLS_RSA_PSK_WITH_RC4_128_SHA'
           algorithm.";
        reference
          "RFC 4279:
             Pre-Shared Key Ciphersuites for Transport Layer Security
             (TLS)
           RFC 6347:
             Datagram Transport Layer Security Version 1.2";
      }
      enum TLS_RSA_PSK_WITH_3DES_EDE_CBC_SHA {
        status deprecated;
        description
          "Enumeration for the 'TLS_RSA_PSK_WITH_3DES_EDE_CBC_SHA'
           algorithm.";
        reference
          "RFC 4279:
             Pre-Shared Key Ciphersuites for Transport Layer Security
             (TLS)";
      }
      enum TLS_RSA_PSK_WITH_AES_128_CBC_SHA {
        status deprecated;
        description
          "Enumeration for the 'TLS_RSA_PSK_WITH_AES_128_CBC_SHA'
           algorithm.";
        reference
          "RFC 4279:
             Pre-Shared Key Ciphersuites for Transport Layer Security
             (TLS)";
      }
      enum TLS_RSA_PSK_WITH_AES_256_CBC_SHA {
        status deprecated;
        description
          "Enumeration for the 'TLS_RSA_PSK_WITH_AES_256_CBC_SHA'
           algorithm.";
        reference
          "RFC 4279:
             Pre-Shared Key Ciphersuites for Transport Layer Security
             (TLS)";
      }
      enum TLS_RSA_WITH_SEED_CBC_SHA {
        status deprecated;
        description
          "Enumeration for the 'TLS_RSA_WITH_SEED_CBC_SHA'
           algorithm.";
        reference
          "RFC 4162:
             Addition of SEED Cipher Suites to Transport Layer
             Security (TLS)";
      }
      enum TLS_DH_DSS_WITH_SEED_CBC_SHA {
        status deprecated;
        description
          "Enumeration for the 'TLS_DH_DSS_WITH_SEED_CBC_SHA'
           algorithm.";
        reference
          "RFC 4162:
             Addition of SEED Cipher Suites to Transport Layer
             Security (TLS)";
      }
      enum TLS_DH_RSA_WITH_SEED_CBC_SHA {
        status deprecated;
        description
          "Enumeration for the 'TLS_DH_RSA_WITH_SEED_CBC_SHA'
           algorithm.";
        reference
          "RFC 4162:
             Addition of SEED Cipher Suites to Transport Layer
             Security (TLS)";
      }
      enum TLS_DHE_DSS_WITH_SEED_CBC_SHA {
        status deprecated;
        description
          "Enumeration for the 'TLS_DHE_DSS_WITH_SEED_CBC_SHA'
           algorithm.";
        reference
          "RFC 4162:
             Addition of SEED Cipher Suites to Transport Layer
             Security (TLS)";
      }
      enum TLS_DHE_RSA_WITH_SEED_CBC_SHA {
        status deprecated;
        description
          "Enumeration for the 'TLS_DHE_RSA_WITH_SEED_CBC_SHA'
           algorithm.";
        reference
          "RFC 4162:
             Addition of SEED Cipher Suites to Transport Layer
             Security (TLS)";
      }
      enum TLS_DH_anon_WITH_SEED_CBC_SHA {
        status deprecated;
        description
          "Enumeration for the 'TLS_DH_anon_WITH_SEED_CBC_SHA'
           algorithm.";
        reference
          "RFC 4162:
             Addition of SEED Cipher Suites to Transport Layer
             Security (TLS)";
      }
      enum TLS_RSA_WITH_AES_128_GCM_SHA256 {
        status deprecated;
        description
          "Enumeration for the 'TLS_RSA_WITH_AES_128_GCM_SHA256'
           algorithm.";
        reference
          "RFC 5288:
             AES Galois Counter Mode (GCM) Cipher Suites for TLS";
      }
      enum TLS_RSA_WITH_AES_256_GCM_SHA384 {
        status deprecated;
        description
          "Enumeration for the 'TLS_RSA_WITH_AES_256_GCM_SHA384'
           algorithm.";
        reference
          "RFC 5288:
             AES Galois Counter Mode (GCM) Cipher Suites for TLS";
      }
      enum TLS_DHE_RSA_WITH_AES_128_GCM_SHA256 {
        description
          "Enumeration for the 'TLS_DHE_RSA_WITH_AES_128_GCM_SHA256'
           algorithm.";
        reference
          "RFC 5288:
             AES Galois Counter Mode (GCM) Cipher Suites for TLS";
      }
      enum TLS_DHE_RSA_WITH_AES_256_GCM_SHA384 {
        description
          "Enumeration for the 'TLS_DHE_RSA_WITH_AES_256_GCM_SHA384'
           algorithm.";
        reference
          "RFC 5288:
             AES Galois Counter Mode (GCM) Cipher Suites for TLS";
      }
      enum TLS_DH_RSA_WITH_AES_128_GCM_SHA256 {
        status deprecated;
        description
          "Enumeration for the 'TLS_DH_RSA_WITH_AES_128_GCM_SHA256'
           algorithm.";
        reference
          "RFC 5288:
             AES Galois Counter Mode (GCM) Cipher Suites for TLS";
      }
      enum TLS_DH_RSA_WITH_AES_256_GCM_SHA384 {
        status deprecated;
        description
          "Enumeration for the 'TLS_DH_RSA_WITH_AES_256_GCM_SHA384'
           algorithm.";
        reference
          "RFC 5288:
             AES Galois Counter Mode (GCM) Cipher Suites for TLS";
      }
      enum TLS_DHE_DSS_WITH_AES_128_GCM_SHA256 {
        status deprecated;
        description
          "Enumeration for the 'TLS_DHE_DSS_WITH_AES_128_GCM_SHA256'
           algorithm.";
        reference
          "RFC 5288:
             AES Galois Counter Mode (GCM) Cipher Suites for TLS";
      }
      enum TLS_DHE_DSS_WITH_AES_256_GCM_SHA384 {
        status deprecated;
        description
          "Enumeration for the 'TLS_DHE_DSS_WITH_AES_256_GCM_SHA384'
           algorithm.";
        reference
          "RFC 5288:
             AES Galois Counter Mode (GCM) Cipher Suites for TLS";
      }
      enum TLS_DH_DSS_WITH_AES_128_GCM_SHA256 {
        status deprecated;
        description
          "Enumeration for the 'TLS_DH_DSS_WITH_AES_128_GCM_SHA256'
           algorithm.";
        reference
          "RFC 5288:
             AES Galois Counter Mode (GCM) Cipher Suites for TLS";
      }
      enum TLS_DH_DSS_WITH_AES_256_GCM_SHA384 {
        status deprecated;
        description
          "Enumeration for the 'TLS_DH_DSS_WITH_AES_256_GCM_SHA384'
           algorithm.";
        reference
          "RFC 5288:
             AES Galois Counter Mode (GCM) Cipher Suites for TLS";
      }
      enum TLS_DH_anon_WITH_AES_128_GCM_SHA256 {
        status deprecated;
        description
          "Enumeration for the 'TLS_DH_anon_WITH_AES_128_GCM_SHA256'
           algorithm.";
        reference
          "RFC 5288:
             AES Galois Counter Mode (GCM) Cipher Suites for TLS";
      }
      enum TLS_DH_anon_WITH_AES_256_GCM_SHA384 {
        status deprecated;
        description
          "Enumeration for the 'TLS_DH_anon_WITH_AES_256_GCM_SHA384'
           algorithm.";
        reference
          "RFC 5288:
             AES Galois Counter Mode (GCM) Cipher Suites for TLS";
      }
      enum TLS_PSK_WITH_AES_128_GCM_SHA256 {
        status deprecated;
        description
          "Enumeration for the 'TLS_PSK_WITH_AES_128_GCM_SHA256'
           algorithm.";
        reference
          "RFC 5487:
             Pre-Shared Key Cipher Suites for TLS with SHA-256/384
             and AES Galois Counter Mode";
      }
      enum TLS_PSK_WITH_AES_256_GCM_SHA384 {
        status deprecated;
        description
          "Enumeration for the 'TLS_PSK_WITH_AES_256_GCM_SHA384'
           algorithm.";
        reference
          "RFC 5487:
             Pre-Shared Key Cipher Suites for TLS with SHA-256/384
             and AES Galois Counter Mode";
      }
      enum TLS_DHE_PSK_WITH_AES_128_GCM_SHA256 {
        description
          "Enumeration for the 'TLS_DHE_PSK_WITH_AES_128_GCM_SHA256'
           algorithm.";
        reference
          "RFC 5487:
             Pre-Shared Key Cipher Suites for TLS with SHA-256/384
             and AES Galois Counter Mode";
      }
      enum TLS_DHE_PSK_WITH_AES_256_GCM_SHA384 {
        description
          "Enumeration for the 'TLS_DHE_PSK_WITH_AES_256_GCM_SHA384'
           algorithm.";
        reference
          "RFC 5487:
             Pre-Shared Key Cipher Suites for TLS with SHA-256/384
             and AES Galois Counter Mode";
      }
      enum TLS_RSA_PSK_WITH_AES_128_GCM_SHA256 {
        status deprecated;
        description
          "Enumeration for the 'TLS_RSA_PSK_WITH_AES_128_GCM_SHA256'
           algorithm.";
        reference
          "RFC 5487:
             Pre-Shared Key Cipher Suites for TLS with SHA-256/384
             and AES Galois Counter Mode";
      }
      enum TLS_RSA_PSK_WITH_AES_256_GCM_SHA384 {
        status deprecated;
        description
          "Enumeration for the 'TLS_RSA_PSK_WITH_AES_256_GCM_SHA384'
           algorithm.";
        reference
          "RFC 5487:
             Pre-Shared Key Cipher Suites for TLS with SHA-256/384
             and AES Galois Counter Mode";
      }
      enum TLS_PSK_WITH_AES_128_CBC_SHA256 {
        status deprecated;
        description
          "Enumeration for the 'TLS_PSK_WITH_AES_128_CBC_SHA256'
           algorithm.";
        reference
          "RFC 5487:
             Pre-Shared Key Cipher Suites for TLS with SHA-256/384
             and AES Galois Counter Mode";
      }
      enum TLS_PSK_WITH_AES_256_CBC_SHA384 {
        status deprecated;
        description
          "Enumeration for the 'TLS_PSK_WITH_AES_256_CBC_SHA384'
           algorithm.";
        reference
          "RFC 5487:
             Pre-Shared Key Cipher Suites for TLS with SHA-256/384
             and AES Galois Counter Mode";
      }
      enum TLS_PSK_WITH_NULL_SHA256 {
        status deprecated;
        description
          "Enumeration for the 'TLS_PSK_WITH_NULL_SHA256'
           algorithm.";
        reference
          "RFC 5487:
             Pre-Shared Key Cipher Suites for TLS with SHA-256/384
             and AES Galois Counter Mode";
      }
      enum TLS_PSK_WITH_NULL_SHA384 {
        status deprecated;
        description
          "Enumeration for the 'TLS_PSK_WITH_NULL_SHA384'
           algorithm.";
        reference
          "RFC 5487:
             Pre-Shared Key Cipher Suites for TLS with SHA-256/384
             and AES Galois Counter Mode";
      }
      enum TLS_DHE_PSK_WITH_AES_128_CBC_SHA256 {
        status deprecated;
        description
          "Enumeration for the 'TLS_DHE_PSK_WITH_AES_128_CBC_SHA256'
           algorithm.";
        reference
          "RFC 5487:
             Pre-Shared Key Cipher Suites for TLS with SHA-256/384
             and AES Galois Counter Mode";
      }
      enum TLS_DHE_PSK_WITH_AES_256_CBC_SHA384 {
        status deprecated;
        description
          "Enumeration for the 'TLS_DHE_PSK_WITH_AES_256_CBC_SHA384'
           algorithm.";
        reference
          "RFC 5487:
             Pre-Shared Key Cipher Suites for TLS with SHA-256/384
             and AES Galois Counter Mode";
      }
      enum TLS_DHE_PSK_WITH_NULL_SHA256 {
        status deprecated;
        description
          "Enumeration for the 'TLS_DHE_PSK_WITH_NULL_SHA256'
           algorithm.";
        reference
          "RFC 5487:
             Pre-Shared Key Cipher Suites for TLS with SHA-256/384
             and AES Galois Counter Mode";
      }
      enum TLS_DHE_PSK_WITH_NULL_SHA384 {
        status deprecated;
        description
          "Enumeration for the 'TLS_DHE_PSK_WITH_NULL_SHA384'
           algorithm.";
        reference
          "RFC 5487:
             Pre-Shared Key Cipher Suites for TLS with SHA-256/384
             and AES Galois Counter Mode";
      }
      enum TLS_RSA_PSK_WITH_AES_128_CBC_SHA256 {
        status deprecated;
        description
          "Enumeration for the 'TLS_RSA_PSK_WITH_AES_128_CBC_SHA256'
           algorithm.";
        reference
          "RFC 5487:
             Pre-Shared Key Cipher Suites for TLS with SHA-256/384
             and AES Galois Counter Mode";
      }
      enum TLS_RSA_PSK_WITH_AES_256_CBC_SHA384 {
        status deprecated;
        description
          "Enumeration for the 'TLS_RSA_PSK_WITH_AES_256_CBC_SHA384'
           algorithm.";
        reference
          "RFC 5487:
             Pre-Shared Key Cipher Suites for TLS with SHA-256/384
             and AES Galois Counter Mode";
      }
      enum TLS_RSA_PSK_WITH_NULL_SHA256 {
        status deprecated;
        description
          "Enumeration for the 'TLS_RSA_PSK_WITH_NULL_SHA256'
           algorithm.";
        reference
          "RFC 5487:
             Pre-Shared Key Cipher Suites for TLS with SHA-256/384
             and AES Galois Counter Mode";
      }
      enum TLS_RSA_PSK_WITH_NULL_SHA384 {
        status deprecated;
        description
          "Enumeration for the 'TLS_RSA_PSK_WITH_NULL_SHA384'
           algorithm.";
        reference
          "RFC 5487:
             Pre-Shared Key Cipher Suites for TLS with SHA-256/384
             and AES Galois Counter Mode";
      }
      enum TLS_RSA_WITH_CAMELLIA_128_CBC_SHA256 {
        status deprecated;
        description
          "Enumeration for the 'TLS_RSA_WITH_CAMELLIA_128_CBC_SHA256'
           algorithm.";
        reference
          "RFC 5932:
             Camellia Cipher Suites for TLS";
      }
      enum TLS_DH_DSS_WITH_CAMELLIA_128_CBC_SHA256 {
        status deprecated;
        description
          "Enumeration for the
           'TLS_DH_DSS_WITH_CAMELLIA_128_CBC_SHA256' algorithm.";
        reference
          "RFC 5932:
             Camellia Cipher Suites for TLS";
      }
      enum TLS_DH_RSA_WITH_CAMELLIA_128_CBC_SHA256 {
        status deprecated;
        description
          "Enumeration for the
           'TLS_DH_RSA_WITH_CAMELLIA_128_CBC_SHA256' algorithm.";
        reference
          "RFC 5932:
             Camellia Cipher Suites for TLS";
      }
      enum TLS_DHE_DSS_WITH_CAMELLIA_128_CBC_SHA256 {
        status deprecated;
        description
          "Enumeration for the
           'TLS_DHE_DSS_WITH_CAMELLIA_128_CBC_SHA256' algorithm.";
        reference
          "RFC 5932:
             Camellia Cipher Suites for TLS";
      }
      enum TLS_DHE_RSA_WITH_CAMELLIA_128_CBC_SHA256 {
        status deprecated;
        description
          "Enumeration for the
           'TLS_DHE_RSA_WITH_CAMELLIA_128_CBC_SHA256' algorithm.";
        reference
          "RFC 5932:
             Camellia Cipher Suites for TLS";
      }
      enum TLS_DH_anon_WITH_CAMELLIA_128_CBC_SHA256 {
        status deprecated;
        description
          "Enumeration for the
           'TLS_DH_anon_WITH_CAMELLIA_128_CBC_SHA256' algorithm.";
        reference
          "RFC 5932:
             Camellia Cipher Suites for TLS";
      }
      enum TLS_RSA_WITH_CAMELLIA_256_CBC_SHA256 {
        status deprecated;
        description
          "Enumeration for the 'TLS_RSA_WITH_CAMELLIA_256_CBC_SHA256'
           algorithm.";
        reference
          "RFC 5932:
             Camellia Cipher Suites for TLS";
      }
      enum TLS_DH_DSS_WITH_CAMELLIA_256_CBC_SHA256 {
        status deprecated;
        description
          "Enumeration for the
           'TLS_DH_DSS_WITH_CAMELLIA_256_CBC_SHA256' algorithm.";
        reference
          "RFC 5932:
             Camellia Cipher Suites for TLS";
      }
      enum TLS_DH_RSA_WITH_CAMELLIA_256_CBC_SHA256 {
        status deprecated;
        description
          "Enumeration for the
           'TLS_DH_RSA_WITH_CAMELLIA_256_CBC_SHA256' algorithm.";
        reference
          "RFC 5932:
             Camellia Cipher Suites for TLS";
      }
      enum TLS_DHE_DSS_WITH_CAMELLIA_256_CBC_SHA256 {
        status deprecated;
        description
          "Enumeration for the
           'TLS_DHE_DSS_WITH_CAMELLIA_256_CBC_SHA256' algorithm.";
        reference
          "RFC 5932:
             Camellia Cipher Suites for TLS";
      }
      enum TLS_DHE_RSA_WITH_CAMELLIA_256_CBC_SHA256 {
        status deprecated;
        description
          "Enumeration for the
           'TLS_DHE_RSA_WITH_CAMELLIA_256_CBC_SHA256' algorithm.";
        reference
          "RFC 5932:
             Camellia Cipher Suites for TLS";
      }
      enum TLS_DH_anon_WITH_CAMELLIA_256_CBC_SHA256 {
        status deprecated;
        description
          "Enumeration for the
           'TLS_DH_anon_WITH_CAMELLIA_256_CBC_SHA256' algorithm.";
        reference
          "RFC 5932:
             Camellia Cipher Suites for TLS";
      }
      enum TLS_SM4_GCM_SM3 {
        status deprecated;
        description
          "Enumeration for the 'TLS_SM4_GCM_SM3' algorithm.";
        reference
          "RFC 8998:
             ShangMi (SM) Cipher Suites for TLS 1.3";
      }
      enum TLS_SM4_CCM_SM3 {
        status deprecated;
        description
          "Enumeration for the 'TLS_SM4_CCM_SM3' algorithm.";
        reference
          "RFC 8998:
             ShangMi (SM) Cipher Suites for TLS 1.3";
      }
      enum TLS_EMPTY_RENEGOTIATION_INFO_SCSV {
        status deprecated;
        description
          "Enumeration for the 'TLS_EMPTY_RENEGOTIATION_INFO_SCSV'
           algorithm.";
        reference
          "RFC 5746:
             Transport Layer Security (TLS) Renegotiation Indication
             Extension";
      }
      enum TLS_AES_128_GCM_SHA256 {
        description
          "Enumeration for the 'TLS_AES_128_GCM_SHA256' algorithm.";
        reference
          "RFC 8446:
             The Transport Layer Security (TLS) Protocol Version
             1.3";
      }
      enum TLS_AES_256_GCM_SHA384 {
        description
          "Enumeration for the 'TLS_AES_256_GCM_SHA384' algorithm.";
        reference
          "RFC 8446:
             The Transport Layer Security (TLS) Protocol Version
             1.3";
      }
      enum TLS_CHACHA20_POLY1305_SHA256 {
        description
          "Enumeration for the 'TLS_CHACHA20_POLY1305_SHA256'
           algorithm.";
        reference
          "RFC 8446:
             The Transport Layer Security (TLS) Protocol Version
             1.3";
      }
      enum TLS_AES_128_CCM_SHA256 {
        description
          "Enumeration for the 'TLS_AES_128_CCM_SHA256' algorithm.";
        reference
          "RFC 8446:
             The Transport Layer Security (TLS) Protocol Version
             1.3";
      }
      enum TLS_AES_128_CCM_8_SHA256 {
        status deprecated;
        description
          "Enumeration for the 'TLS_AES_128_CCM_8_SHA256'
           algorithm.";
        reference
          "RFC 8446:
             The Transport Layer Security (TLS) Protocol Version 1.3
           IESG Action:
             IESG Action 2018-08-16";
      }
      enum TLS_AEGIS_256_SHA512 {
        status deprecated;
        description
          "Enumeration for the 'TLS_AEGIS_256_SHA512' algorithm.";
        reference
          "draft-irtf-cfrg-aegis-aead-08:
             The AEGIS Family of Authenticated Encryption
             Algorithms";
      }
      enum TLS_AEGIS_128L_SHA256 {
        status deprecated;
        description
          "Enumeration for the 'TLS_AEGIS_128L_SHA256' algorithm.";
        reference
          "draft-irtf-cfrg-aegis-aead-08:
             The AEGIS Family of Authenticated Encryption
             Algorithms";
      }
      enum TLS_FALLBACK_SCSV {
        status deprecated;
        description
          "Enumeration for the 'TLS_FALLBACK_SCSV' algorithm.";
        reference
          "RFC 7507:
             TLS Fallback Signaling Cipher Suite Value (SCSV) for
             Preventing Protocol Downgrade Attacks";
      }
      enum TLS_ECDH_ECDSA_WITH_NULL_SHA {
        status deprecated;
        description
          "Enumeration for the 'TLS_ECDH_ECDSA_WITH_NULL_SHA'
           algorithm.";
        reference
          "RFC 8422:
             Elliptic Curve Cryptography (ECC) Cipher Suites for
             Transport Layer Security (TLS) Versions 1.2 and
             Earlier";
      }
      enum TLS_ECDH_ECDSA_WITH_RC4_128_SHA {
        status deprecated;
        description
          "Enumeration for the 'TLS_ECDH_ECDSA_WITH_RC4_128_SHA'
           algorithm.";
        reference
          "RFC 8422:
             Elliptic Curve Cryptography (ECC) Cipher Suites for
             Transport Layer Security (TLS) Versions 1.2 and Earlier
           RFC 6347:
             Datagram Transport Layer Security Version 1.2";
      }
      enum TLS_ECDH_ECDSA_WITH_3DES_EDE_CBC_SHA {
        status deprecated;
        description
          "Enumeration for the 'TLS_ECDH_ECDSA_WITH_3DES_EDE_CBC_SHA'
           algorithm.";
        reference
          "RFC 8422:
             Elliptic Curve Cryptography (ECC) Cipher Suites for
             Transport Layer Security (TLS) Versions 1.2 and
             Earlier";
      }
      enum TLS_ECDH_ECDSA_WITH_AES_128_CBC_SHA {
        status deprecated;
        description
          "Enumeration for the 'TLS_ECDH_ECDSA_WITH_AES_128_CBC_SHA'
           algorithm.";
        reference
          "RFC 8422:
             Elliptic Curve Cryptography (ECC) Cipher Suites for
             Transport Layer Security (TLS) Versions 1.2 and
             Earlier";
      }
      enum TLS_ECDH_ECDSA_WITH_AES_256_CBC_SHA {
        status deprecated;
        description
          "Enumeration for the 'TLS_ECDH_ECDSA_WITH_AES_256_CBC_SHA'
           algorithm.";
        reference
          "RFC 8422:
             Elliptic Curve Cryptography (ECC) Cipher Suites for
             Transport Layer Security (TLS) Versions 1.2 and
             Earlier";
      }
      enum TLS_ECDHE_ECDSA_WITH_NULL_SHA {
        status deprecated;
        description
          "Enumeration for the 'TLS_ECDHE_ECDSA_WITH_NULL_SHA'
           algorithm.";
        reference
          "RFC 8422:
             Elliptic Curve Cryptography (ECC) Cipher Suites for
             Transport Layer Security (TLS) Versions 1.2 and
             Earlier";
      }
      enum TLS_ECDHE_ECDSA_WITH_RC4_128_SHA {
        status deprecated;
        description
          "Enumeration for the 'TLS_ECDHE_ECDSA_WITH_RC4_128_SHA'
           algorithm.";
        reference
          "RFC 8422:
             Elliptic Curve Cryptography (ECC) Cipher Suites for
             Transport Layer Security (TLS) Versions 1.2 and Earlier
           RFC 6347:
             Datagram Transport Layer Security Version 1.2";
      }
      enum TLS_ECDHE_ECDSA_WITH_3DES_EDE_CBC_SHA {
        status deprecated;
        description
          "Enumeration for the
           'TLS_ECDHE_ECDSA_WITH_3DES_EDE_CBC_SHA' algorithm.";
        reference
          "RFC 8422:
             Elliptic Curve Cryptography (ECC) Cipher Suites for
             Transport Layer Security (TLS) Versions 1.2 and
             Earlier";
      }
      enum TLS_ECDHE_ECDSA_WITH_AES_128_CBC_SHA {
        status deprecated;
        description
          "Enumeration for the 'TLS_ECDHE_ECDSA_WITH_AES_128_CBC_SHA'
           algorithm.";
        reference
          "RFC 8422:
             Elliptic Curve Cryptography (ECC) Cipher Suites for
             Transport Layer Security (TLS) Versions 1.2 and
             Earlier";
      }
      enum TLS_ECDHE_ECDSA_WITH_AES_256_CBC_SHA {
        status deprecated;
        description
          "Enumeration for the 'TLS_ECDHE_ECDSA_WITH_AES_256_CBC_SHA'
           algorithm.";
        reference
          "RFC 8422:
             Elliptic Curve Cryptography (ECC) Cipher Suites for
             Transport Layer Security (TLS) Versions 1.2 and
             Earlier";
      }
      enum TLS_ECDH_RSA_WITH_NULL_SHA {
        status deprecated;
        description
          "Enumeration for the 'TLS_ECDH_RSA_WITH_NULL_SHA'
           algorithm.";
        reference
          "RFC 8422:
             Elliptic Curve Cryptography (ECC) Cipher Suites for
             Transport Layer Security (TLS) Versions 1.2 and
             Earlier";
      }
      enum TLS_ECDH_RSA_WITH_RC4_128_SHA {
        status deprecated;
        description
          "Enumeration for the 'TLS_ECDH_RSA_WITH_RC4_128_SHA'
           algorithm.";
        reference
          "RFC 8422:
             Elliptic Curve Cryptography (ECC) Cipher Suites for
             Transport Layer Security (TLS) Versions 1.2 and Earlier
           RFC 6347:
             Datagram Transport Layer Security Version 1.2";
      }
      enum TLS_ECDH_RSA_WITH_3DES_EDE_CBC_SHA {
        status deprecated;
        description
          "Enumeration for the 'TLS_ECDH_RSA_WITH_3DES_EDE_CBC_SHA'
           algorithm.";
        reference
          "RFC 8422:
             Elliptic Curve Cryptography (ECC) Cipher Suites for
             Transport Layer Security (TLS) Versions 1.2 and
             Earlier";
      }
      enum TLS_ECDH_RSA_WITH_AES_128_CBC_SHA {
        status deprecated;
        description
          "Enumeration for the 'TLS_ECDH_RSA_WITH_AES_128_CBC_SHA'
           algorithm.";
        reference
          "RFC 8422:
             Elliptic Curve Cryptography (ECC) Cipher Suites for
             Transport Layer Security (TLS) Versions 1.2 and
             Earlier";
      }
      enum TLS_ECDH_RSA_WITH_AES_256_CBC_SHA {
        status deprecated;
        description
          "Enumeration for the 'TLS_ECDH_RSA_WITH_AES_256_CBC_SHA'
           algorithm.";
        reference
          "RFC 8422:
             Elliptic Curve Cryptography (ECC) Cipher Suites for
             Transport Layer Security (TLS) Versions 1.2 and
             Earlier";
      }
      enum TLS_ECDHE_RSA_WITH_NULL_SHA {
        status deprecated;
        description
          "Enumeration for the 'TLS_ECDHE_RSA_WITH_NULL_SHA'
           algorithm.";
        reference
          "RFC 8422:
             Elliptic Curve Cryptography (ECC) Cipher Suites for
             Transport Layer Security (TLS) Versions 1.2 and
             Earlier";
      }
      enum TLS_ECDHE_RSA_WITH_RC4_128_SHA {
        status deprecated;
        description
          "Enumeration for the 'TLS_ECDHE_RSA_WITH_RC4_128_SHA'
           algorithm.";
        reference
          "RFC 8422:
             Elliptic Curve Cryptography (ECC) Cipher Suites for
             Transport Layer Security (TLS) Versions 1.2 and Earlier
           RFC 6347:
             Datagram Transport Layer Security Version 1.2";
      }
      enum TLS_ECDHE_RSA_WITH_3DES_EDE_CBC_SHA {
        status deprecated;
        description
          "Enumeration for the 'TLS_ECDHE_RSA_WITH_3DES_EDE_CBC_SHA'
           algorithm.";
        reference
          "RFC 8422:
             Elliptic Curve Cryptography (ECC) Cipher Suites for
             Transport Layer Security (TLS) Versions 1.2 and
             Earlier";
      }
      enum TLS_ECDHE_RSA_WITH_AES_128_CBC_SHA {
        status deprecated;
        description
          "Enumeration for the 'TLS_ECDHE_RSA_WITH_AES_128_CBC_SHA'
           algorithm.";
        reference
          "RFC 8422:
             Elliptic Curve Cryptography (ECC) Cipher Suites for
             Transport Layer Security (TLS) Versions 1.2 and
             Earlier";
      }
      enum TLS_ECDHE_RSA_WITH_AES_256_CBC_SHA {
        status deprecated;
        description
          "Enumeration for the 'TLS_ECDHE_RSA_WITH_AES_256_CBC_SHA'
           algorithm.";
        reference
          "RFC 8422:
             Elliptic Curve Cryptography (ECC) Cipher Suites for
             Transport Layer Security (TLS) Versions 1.2 and
             Earlier";
      }
      enum TLS_ECDH_anon_WITH_NULL_SHA {
        status deprecated;
        description
          "Enumeration for the 'TLS_ECDH_anon_WITH_NULL_SHA'
           algorithm.";
        reference
          "RFC 8422:
             Elliptic Curve Cryptography (ECC) Cipher Suites for
             Transport Layer Security (TLS) Versions 1.2 and
             Earlier";
      }
      enum TLS_ECDH_anon_WITH_RC4_128_SHA {
        status deprecated;
        description
          "Enumeration for the 'TLS_ECDH_anon_WITH_RC4_128_SHA'
           algorithm.";
        reference
          "RFC 8422:
             Elliptic Curve Cryptography (ECC) Cipher Suites for
             Transport Layer Security (TLS) Versions 1.2 and Earlier
           RFC 6347:
             Datagram Transport Layer Security Version 1.2";
      }
      enum TLS_ECDH_anon_WITH_3DES_EDE_CBC_SHA {
        status deprecated;
        description
          "Enumeration for the 'TLS_ECDH_anon_WITH_3DES_EDE_CBC_SHA'
           algorithm.";
        reference
          "RFC 8422:
             Elliptic Curve Cryptography (ECC) Cipher Suites for
             Transport Layer Security (TLS) Versions 1.2 and
             Earlier";
      }
      enum TLS_ECDH_anon_WITH_AES_128_CBC_SHA {
        status deprecated;
        description
          "Enumeration for the 'TLS_ECDH_anon_WITH_AES_128_CBC_SHA'
           algorithm.";
        reference
          "RFC 8422:
             Elliptic Curve Cryptography (ECC) Cipher Suites for
             Transport Layer Security (TLS) Versions 1.2 and
             Earlier";
      }
      enum TLS_ECDH_anon_WITH_AES_256_CBC_SHA {
        status deprecated;
        description
          "Enumeration for the 'TLS_ECDH_anon_WITH_AES_256_CBC_SHA'
           algorithm.";
        reference
          "RFC 8422:
             Elliptic Curve Cryptography (ECC) Cipher Suites for
             Transport Layer Security (TLS) Versions 1.2 and
             Earlier";
      }
      enum TLS_SRP_SHA_WITH_3DES_EDE_CBC_SHA {
        status deprecated;
        description
          "Enumeration for the 'TLS_SRP_SHA_WITH_3DES_EDE_CBC_SHA'
           algorithm.";
        reference
          "RFC 5054:
             Using the Secure Remote Password (SRP) Protocol for TLS
             Authentication";
      }
      enum TLS_SRP_SHA_RSA_WITH_3DES_EDE_CBC_SHA {
        status deprecated;
        description
          "Enumeration for the
           'TLS_SRP_SHA_RSA_WITH_3DES_EDE_CBC_SHA' algorithm.";
        reference
          "RFC 5054:
             Using the Secure Remote Password (SRP) Protocol for TLS
             Authentication";
      }
      enum TLS_SRP_SHA_DSS_WITH_3DES_EDE_CBC_SHA {
        status deprecated;
        description
          "Enumeration for the
           'TLS_SRP_SHA_DSS_WITH_3DES_EDE_CBC_SHA' algorithm.";
        reference
          "RFC 5054:
             Using the Secure Remote Password (SRP) Protocol for TLS
             Authentication";
      }
      enum TLS_SRP_SHA_WITH_AES_128_CBC_SHA {
        status deprecated;
        description
          "Enumeration for the 'TLS_SRP_SHA_WITH_AES_128_CBC_SHA'
           algorithm.";
        reference
          "RFC 5054:
             Using the Secure Remote Password (SRP) Protocol for TLS
             Authentication";
      }
      enum TLS_SRP_SHA_RSA_WITH_AES_128_CBC_SHA {
        status deprecated;
        description
          "Enumeration for the 'TLS_SRP_SHA_RSA_WITH_AES_128_CBC_SHA'
           algorithm.";
        reference
          "RFC 5054:
             Using the Secure Remote Password (SRP) Protocol for TLS
             Authentication";
      }
      enum TLS_SRP_SHA_DSS_WITH_AES_128_CBC_SHA {
        status deprecated;
        description
          "Enumeration for the 'TLS_SRP_SHA_DSS_WITH_AES_128_CBC_SHA'
           algorithm.";
        reference
          "RFC 5054:
             Using the Secure Remote Password (SRP) Protocol for TLS
             Authentication";
      }
      enum TLS_SRP_SHA_WITH_AES_256_CBC_SHA {
        status deprecated;
        description
          "Enumeration for the 'TLS_SRP_SHA_WITH_AES_256_CBC_SHA'
           algorithm.";
        reference
          "RFC 5054:
             Using the Secure Remote Password (SRP) Protocol for TLS
             Authentication";
      }
      enum TLS_SRP_SHA_RSA_WITH_AES_256_CBC_SHA {
        status deprecated;
        description
          "Enumeration for the 'TLS_SRP_SHA_RSA_WITH_AES_256_CBC_SHA'
           algorithm.";
        reference
          "RFC 5054:
             Using the Secure Remote Password (SRP) Protocol for TLS
             Authentication";
      }
      enum TLS_SRP_SHA_DSS_WITH_AES_256_CBC_SHA {
        status deprecated;
        description
          "Enumeration for the 'TLS_SRP_SHA_DSS_WITH_AES_256_CBC_SHA'
           algorithm.";
        reference
          "RFC 5054:
             Using the Secure Remote Password (SRP) Protocol for TLS
             Authentication";
      }
      enum TLS_ECDHE_ECDSA_WITH_AES_128_CBC_SHA256 {
        status deprecated;
        description
          "Enumeration for the
           'TLS_ECDHE_ECDSA_WITH_AES_128_CBC_SHA256' algorithm.";
        reference
          "RFC 5289:
             TLS Elliptic Curve Cipher Suites with SHA-256/384 and
             AES Galois Counter Mode (GCM)";
      }
      enum TLS_ECDHE_ECDSA_WITH_AES_256_CBC_SHA384 {
        status deprecated;
        description
          "Enumeration for the
           'TLS_ECDHE_ECDSA_WITH_AES_256_CBC_SHA384' algorithm.";
        reference
          "RFC 5289:
             TLS Elliptic Curve Cipher Suites with SHA-256/384 and
             AES Galois Counter Mode (GCM)";
      }
      enum TLS_ECDH_ECDSA_WITH_AES_128_CBC_SHA256 {
        status deprecated;
        description
          "Enumeration for the
           'TLS_ECDH_ECDSA_WITH_AES_128_CBC_SHA256' algorithm.";
        reference
          "RFC 5289:
             TLS Elliptic Curve Cipher Suites with SHA-256/384 and
             AES Galois Counter Mode (GCM)";
      }
      enum TLS_ECDH_ECDSA_WITH_AES_256_CBC_SHA384 {
        status deprecated;
        description
          "Enumeration for the
           'TLS_ECDH_ECDSA_WITH_AES_256_CBC_SHA384' algorithm.";
        reference
          "RFC 5289:
             TLS Elliptic Curve Cipher Suites with SHA-256/384 and
             AES Galois Counter Mode (GCM)";
      }
      enum TLS_ECDHE_RSA_WITH_AES_128_CBC_SHA256 {
        status deprecated;
        description
          "Enumeration for the
           'TLS_ECDHE_RSA_WITH_AES_128_CBC_SHA256' algorithm.";
        reference
          "RFC 5289:
             TLS Elliptic Curve Cipher Suites with SHA-256/384 and
             AES Galois Counter Mode (GCM)";
      }
      enum TLS_ECDHE_RSA_WITH_AES_256_CBC_SHA384 {
        status deprecated;
        description
          "Enumeration for the
           'TLS_ECDHE_RSA_WITH_AES_256_CBC_SHA384' algorithm.";
        reference
          "RFC 5289:
             TLS Elliptic Curve Cipher Suites with SHA-256/384 and
             AES Galois Counter Mode (GCM)";
      }
      enum TLS_ECDH_RSA_WITH_AES_128_CBC_SHA256 {
        status deprecated;
        description
          "Enumeration for the 'TLS_ECDH_RSA_WITH_AES_128_CBC_SHA256'
           algorithm.";
        reference
          "RFC 5289:
             TLS Elliptic Curve Cipher Suites with SHA-256/384 and
             AES Galois Counter Mode (GCM)";
      }
      enum TLS_ECDH_RSA_WITH_AES_256_CBC_SHA384 {
        status deprecated;
        description
          "Enumeration for the 'TLS_ECDH_RSA_WITH_AES_256_CBC_SHA384'
           algorithm.";
        reference
          "RFC 5289:
             TLS Elliptic Curve Cipher Suites with SHA-256/384 and
             AES Galois Counter Mode (GCM)";
      }
      enum TLS_ECDHE_ECDSA_WITH_AES_128_GCM_SHA256 {
        description
          "Enumeration for the
           'TLS_ECDHE_ECDSA_WITH_AES_128_GCM_SHA256' algorithm.";
        reference
          "RFC 5289:
             TLS Elliptic Curve Cipher Suites with SHA-256/384 and
             AES Galois Counter Mode (GCM)";
      }
      enum TLS_ECDHE_ECDSA_WITH_AES_256_GCM_SHA384 {
        description
          "Enumeration for the
           'TLS_ECDHE_ECDSA_WITH_AES_256_GCM_SHA384' algorithm.";
        reference
          "RFC 5289:
             TLS Elliptic Curve Cipher Suites with SHA-256/384 and
             AES Galois Counter Mode (GCM)";
      }
      enum TLS_ECDH_ECDSA_WITH_AES_128_GCM_SHA256 {
        status deprecated;
        description
          "Enumeration for the
           'TLS_ECDH_ECDSA_WITH_AES_128_GCM_SHA256' algorithm.";
        reference
          "RFC 5289:
             TLS Elliptic Curve Cipher Suites with SHA-256/384 and
             AES Galois Counter Mode (GCM)";
      }
      enum TLS_ECDH_ECDSA_WITH_AES_256_GCM_SHA384 {
        status deprecated;
        description
          "Enumeration for the
           'TLS_ECDH_ECDSA_WITH_AES_256_GCM_SHA384' algorithm.";
        reference
          "RFC 5289:
             TLS Elliptic Curve Cipher Suites with SHA-256/384 and
             AES Galois Counter Mode (GCM)";
      }
      enum TLS_ECDHE_RSA_WITH_AES_128_GCM_SHA256 {
        description
          "Enumeration for the
           'TLS_ECDHE_RSA_WITH_AES_128_GCM_SHA256' algorithm.";
        reference
          "RFC 5289:
             TLS Elliptic Curve Cipher Suites with SHA-256/384 and
             AES Galois Counter Mode (GCM)";
      }
      enum TLS_ECDHE_RSA_WITH_AES_256_GCM_SHA384 {
        description
          "Enumeration for the
           'TLS_ECDHE_RSA_WITH_AES_256_GCM_SHA384' algorithm.";
        reference
          "RFC 5289:
             TLS Elliptic Curve Cipher Suites with SHA-256/384 and
             AES Galois Counter Mode (GCM)";
      }
      enum TLS_ECDH_RSA_WITH_AES_128_GCM_SHA256 {
        status deprecated;
        description
          "Enumeration for the 'TLS_ECDH_RSA_WITH_AES_128_GCM_SHA256'
           algorithm.";
        reference
          "RFC 5289:
             TLS Elliptic Curve Cipher Suites with SHA-256/384 and
             AES Galois Counter Mode (GCM)";
      }
      enum TLS_ECDH_RSA_WITH_AES_256_GCM_SHA384 {
        status deprecated;
        description
          "Enumeration for the 'TLS_ECDH_RSA_WITH_AES_256_GCM_SHA384'
           algorithm.";
        reference
          "RFC 5289:
             TLS Elliptic Curve Cipher Suites with SHA-256/384 and
             AES Galois Counter Mode (GCM)";
      }
      enum TLS_ECDHE_PSK_WITH_RC4_128_SHA {
        status deprecated;
        description
          "Enumeration for the 'TLS_ECDHE_PSK_WITH_RC4_128_SHA'
           algorithm.";
        reference
          "RFC 5489:
             ECDHE_PSK Cipher Suites for Transport Layer Security
             (TLS)
           RFC 6347:
             Datagram Transport Layer Security Version 1.2";
      }
      enum TLS_ECDHE_PSK_WITH_3DES_EDE_CBC_SHA {
        status deprecated;
        description
          "Enumeration for the 'TLS_ECDHE_PSK_WITH_3DES_EDE_CBC_SHA'
           algorithm.";
        reference
          "RFC 5489:
             ECDHE_PSK Cipher Suites for Transport Layer Security
             (TLS)";
      }
      enum TLS_ECDHE_PSK_WITH_AES_128_CBC_SHA {
        status deprecated;
        description
          "Enumeration for the 'TLS_ECDHE_PSK_WITH_AES_128_CBC_SHA'
           algorithm.";
        reference
          "RFC 5489:
             ECDHE_PSK Cipher Suites for Transport Layer Security
             (TLS)";
      }
      enum TLS_ECDHE_PSK_WITH_AES_256_CBC_SHA {
        status deprecated;
        description
          "Enumeration for the 'TLS_ECDHE_PSK_WITH_AES_256_CBC_SHA'
           algorithm.";
        reference
          "RFC 5489:
             ECDHE_PSK Cipher Suites for Transport Layer Security
             (TLS)";
      }
      enum TLS_ECDHE_PSK_WITH_AES_128_CBC_SHA256 {
        status deprecated;
        description
          "Enumeration for the
           'TLS_ECDHE_PSK_WITH_AES_128_CBC_SHA256' algorithm.";
        reference
          "RFC 5489:
             ECDHE_PSK Cipher Suites for Transport Layer Security
             (TLS)";
      }
      enum TLS_ECDHE_PSK_WITH_AES_256_CBC_SHA384 {
        status deprecated;
        description
          "Enumeration for the
           'TLS_ECDHE_PSK_WITH_AES_256_CBC_SHA384' algorithm.";
        reference
          "RFC 5489:
             ECDHE_PSK Cipher Suites for Transport Layer Security
             (TLS)";
      }
      enum TLS_ECDHE_PSK_WITH_NULL_SHA {
        status deprecated;
        description
          "Enumeration for the 'TLS_ECDHE_PSK_WITH_NULL_SHA'
           algorithm.";
        reference
          "RFC 5489:
             ECDHE_PSK Cipher Suites for Transport Layer Security
             (TLS)";
      }
      enum TLS_ECDHE_PSK_WITH_NULL_SHA256 {
        status deprecated;
        description
          "Enumeration for the 'TLS_ECDHE_PSK_WITH_NULL_SHA256'
           algorithm.";
        reference
          "RFC 5489:
             ECDHE_PSK Cipher Suites for Transport Layer Security
             (TLS)";
      }
      enum TLS_ECDHE_PSK_WITH_NULL_SHA384 {
        status deprecated;
        description
          "Enumeration for the 'TLS_ECDHE_PSK_WITH_NULL_SHA384'
           algorithm.";
        reference
          "RFC 5489:
             ECDHE_PSK Cipher Suites for Transport Layer Security
             (TLS)";
      }
      enum TLS_RSA_WITH_ARIA_128_CBC_SHA256 {
        status deprecated;
        description
          "Enumeration for the 'TLS_RSA_WITH_ARIA_128_CBC_SHA256'
           algorithm.";
        reference
          "RFC 6209:
             Addition of the ARIA Cipher Suites to Transport Layer
             Security (TLS)";
      }
      enum TLS_RSA_WITH_ARIA_256_CBC_SHA384 {
        status deprecated;
        description
          "Enumeration for the 'TLS_RSA_WITH_ARIA_256_CBC_SHA384'
           algorithm.";
        reference
          "RFC 6209:
             Addition of the ARIA Cipher Suites to Transport Layer
             Security (TLS)";
      }
      enum TLS_DH_DSS_WITH_ARIA_128_CBC_SHA256 {
        status deprecated;
        description
          "Enumeration for the 'TLS_DH_DSS_WITH_ARIA_128_CBC_SHA256'
           algorithm.";
        reference
          "RFC 6209:
             Addition of the ARIA Cipher Suites to Transport Layer
             Security (TLS)";
      }
      enum TLS_DH_DSS_WITH_ARIA_256_CBC_SHA384 {
        status deprecated;
        description
          "Enumeration for the 'TLS_DH_DSS_WITH_ARIA_256_CBC_SHA384'
           algorithm.";
        reference
          "RFC 6209:
             Addition of the ARIA Cipher Suites to Transport Layer
             Security (TLS)";
      }
      enum TLS_DH_RSA_WITH_ARIA_128_CBC_SHA256 {
        status deprecated;
        description
          "Enumeration for the 'TLS_DH_RSA_WITH_ARIA_128_CBC_SHA256'
           algorithm.";
        reference
          "RFC 6209:
             Addition of the ARIA Cipher Suites to Transport Layer
             Security (TLS)";
      }
      enum TLS_DH_RSA_WITH_ARIA_256_CBC_SHA384 {
        status deprecated;
        description
          "Enumeration for the 'TLS_DH_RSA_WITH_ARIA_256_CBC_SHA384'
           algorithm.";
        reference
          "RFC 6209:
             Addition of the ARIA Cipher Suites to Transport Layer
             Security (TLS)";
      }
      enum TLS_DHE_DSS_WITH_ARIA_128_CBC_SHA256 {
        status deprecated;
        description
          "Enumeration for the 'TLS_DHE_DSS_WITH_ARIA_128_CBC_SHA256'
           algorithm.";
        reference
          "RFC 6209:
             Addition of the ARIA Cipher Suites to Transport Layer
             Security (TLS)";
      }
      enum TLS_DHE_DSS_WITH_ARIA_256_CBC_SHA384 {
        status deprecated;
        description
          "Enumeration for the 'TLS_DHE_DSS_WITH_ARIA_256_CBC_SHA384'
           algorithm.";
        reference
          "RFC 6209:
             Addition of the ARIA Cipher Suites to Transport Layer
             Security (TLS)";
      }
      enum TLS_DHE_RSA_WITH_ARIA_128_CBC_SHA256 {
        status deprecated;
        description
          "Enumeration for the 'TLS_DHE_RSA_WITH_ARIA_128_CBC_SHA256'
           algorithm.";
        reference
          "RFC 6209:
             Addition of the ARIA Cipher Suites to Transport Layer
             Security (TLS)";
      }
      enum TLS_DHE_RSA_WITH_ARIA_256_CBC_SHA384 {
        status deprecated;
        description
          "Enumeration for the 'TLS_DHE_RSA_WITH_ARIA_256_CBC_SHA384'
           algorithm.";
        reference
          "RFC 6209:
             Addition of the ARIA Cipher Suites to Transport Layer
             Security (TLS)";
      }
      enum TLS_DH_anon_WITH_ARIA_128_CBC_SHA256 {
        status deprecated;
        description
          "Enumeration for the 'TLS_DH_anon_WITH_ARIA_128_CBC_SHA256'
           algorithm.";
        reference
          "RFC 6209:
             Addition of the ARIA Cipher Suites to Transport Layer
             Security (TLS)";
      }
      enum TLS_DH_anon_WITH_ARIA_256_CBC_SHA384 {
        status deprecated;
        description
          "Enumeration for the 'TLS_DH_anon_WITH_ARIA_256_CBC_SHA384'
           algorithm.";
        reference
          "RFC 6209:
             Addition of the ARIA Cipher Suites to Transport Layer
             Security (TLS)";
      }
      enum TLS_ECDHE_ECDSA_WITH_ARIA_128_CBC_SHA256 {
        status deprecated;
        description
          "Enumeration for the
           'TLS_ECDHE_ECDSA_WITH_ARIA_128_CBC_SHA256' algorithm.";
        reference
          "RFC 6209:
             Addition of the ARIA Cipher Suites to Transport Layer
             Security (TLS)";
      }
      enum TLS_ECDHE_ECDSA_WITH_ARIA_256_CBC_SHA384 {
        status deprecated;
        description
          "Enumeration for the
           'TLS_ECDHE_ECDSA_WITH_ARIA_256_CBC_SHA384' algorithm.";
        reference
          "RFC 6209:
             Addition of the ARIA Cipher Suites to Transport Layer
             Security (TLS)";
      }
      enum TLS_ECDH_ECDSA_WITH_ARIA_128_CBC_SHA256 {
        status deprecated;
        description
          "Enumeration for the
           'TLS_ECDH_ECDSA_WITH_ARIA_128_CBC_SHA256' algorithm.";
        reference
          "RFC 6209:
             Addition of the ARIA Cipher Suites to Transport Layer
             Security (TLS)";
      }
      enum TLS_ECDH_ECDSA_WITH_ARIA_256_CBC_SHA384 {
        status deprecated;
        description
          "Enumeration for the
           'TLS_ECDH_ECDSA_WITH_ARIA_256_CBC_SHA384' algorithm.";
        reference
          "RFC 6209:
             Addition of the ARIA Cipher Suites to Transport Layer
             Security (TLS)";
      }
      enum TLS_ECDHE_RSA_WITH_ARIA_128_CBC_SHA256 {
        status deprecated;
        description
          "Enumeration for the
           'TLS_ECDHE_RSA_WITH_ARIA_128_CBC_SHA256' algorithm.";
        reference
          "RFC 6209:
             Addition of the ARIA Cipher Suites to Transport Layer
             Security (TLS)";
      }
      enum TLS_ECDHE_RSA_WITH_ARIA_256_CBC_SHA384 {
        status deprecated;
        description
          "Enumeration for the
           'TLS_ECDHE_RSA_WITH_ARIA_256_CBC_SHA384' algorithm.";
        reference
          "RFC 6209:
             Addition of the ARIA Cipher Suites to Transport Layer
             Security (TLS)";
      }
      enum TLS_ECDH_RSA_WITH_ARIA_128_CBC_SHA256 {
        status deprecated;
        description
          "Enumeration for the
           'TLS_ECDH_RSA_WITH_ARIA_128_CBC_SHA256' algorithm.";
        reference
          "RFC 6209:
             Addition of the ARIA Cipher Suites to Transport Layer
             Security (TLS)";
      }
      enum TLS_ECDH_RSA_WITH_ARIA_256_CBC_SHA384 {
        status deprecated;
        description
          "Enumeration for the
           'TLS_ECDH_RSA_WITH_ARIA_256_CBC_SHA384' algorithm.";
        reference
          "RFC 6209:
             Addition of the ARIA Cipher Suites to Transport Layer
             Security (TLS)";
      }
      enum TLS_RSA_WITH_ARIA_128_GCM_SHA256 {
        status deprecated;
        description
          "Enumeration for the 'TLS_RSA_WITH_ARIA_128_GCM_SHA256'
           algorithm.";
        reference
          "RFC 6209:
             Addition of the ARIA Cipher Suites to Transport Layer
             Security (TLS)";
      }
      enum TLS_RSA_WITH_ARIA_256_GCM_SHA384 {
        status deprecated;
        description
          "Enumeration for the 'TLS_RSA_WITH_ARIA_256_GCM_SHA384'
           algorithm.";
        reference
          "RFC 6209:
             Addition of the ARIA Cipher Suites to Transport Layer
             Security (TLS)";
      }
      enum TLS_DHE_RSA_WITH_ARIA_128_GCM_SHA256 {
        status deprecated;
        description
          "Enumeration for the 'TLS_DHE_RSA_WITH_ARIA_128_GCM_SHA256'
           algorithm.";
        reference
          "RFC 6209:
             Addition of the ARIA Cipher Suites to Transport Layer
             Security (TLS)";
      }
      enum TLS_DHE_RSA_WITH_ARIA_256_GCM_SHA384 {
        status deprecated;
        description
          "Enumeration for the 'TLS_DHE_RSA_WITH_ARIA_256_GCM_SHA384'
           algorithm.";
        reference
          "RFC 6209:
             Addition of the ARIA Cipher Suites to Transport Layer
             Security (TLS)";
      }
      enum TLS_DH_RSA_WITH_ARIA_128_GCM_SHA256 {
        status deprecated;
        description
          "Enumeration for the 'TLS_DH_RSA_WITH_ARIA_128_GCM_SHA256'
           algorithm.";
        reference
          "RFC 6209:
             Addition of the ARIA Cipher Suites to Transport Layer
             Security (TLS)";
      }
      enum TLS_DH_RSA_WITH_ARIA_256_GCM_SHA384 {
        status deprecated;
        description
          "Enumeration for the 'TLS_DH_RSA_WITH_ARIA_256_GCM_SHA384'
           algorithm.";
        reference
          "RFC 6209:
             Addition of the ARIA Cipher Suites to Transport Layer
             Security (TLS)";
      }
      enum TLS_DHE_DSS_WITH_ARIA_128_GCM_SHA256 {
        status deprecated;
        description
          "Enumeration for the 'TLS_DHE_DSS_WITH_ARIA_128_GCM_SHA256'
           algorithm.";
        reference
          "RFC 6209:
             Addition of the ARIA Cipher Suites to Transport Layer
             Security (TLS)";
      }
      enum TLS_DHE_DSS_WITH_ARIA_256_GCM_SHA384 {
        status deprecated;
        description
          "Enumeration for the 'TLS_DHE_DSS_WITH_ARIA_256_GCM_SHA384'
           algorithm.";
        reference
          "RFC 6209:
             Addition of the ARIA Cipher Suites to Transport Layer
             Security (TLS)";
      }
      enum TLS_DH_DSS_WITH_ARIA_128_GCM_SHA256 {
        status deprecated;
        description
          "Enumeration for the 'TLS_DH_DSS_WITH_ARIA_128_GCM_SHA256'
           algorithm.";
        reference
          "RFC 6209:
             Addition of the ARIA Cipher Suites to Transport Layer
             Security (TLS)";
      }
      enum TLS_DH_DSS_WITH_ARIA_256_GCM_SHA384 {
        status deprecated;
        description
          "Enumeration for the 'TLS_DH_DSS_WITH_ARIA_256_GCM_SHA384'
           algorithm.";
        reference
          "RFC 6209:
             Addition of the ARIA Cipher Suites to Transport Layer
             Security (TLS)";
      }
      enum TLS_DH_anon_WITH_ARIA_128_GCM_SHA256 {
        status deprecated;
        description
          "Enumeration for the 'TLS_DH_anon_WITH_ARIA_128_GCM_SHA256'
           algorithm.";
        reference
          "RFC 6209:
             Addition of the ARIA Cipher Suites to Transport Layer
             Security (TLS)";
      }
      enum TLS_DH_anon_WITH_ARIA_256_GCM_SHA384 {
        status deprecated;
        description
          "Enumeration for the 'TLS_DH_anon_WITH_ARIA_256_GCM_SHA384'
           algorithm.";
        reference
          "RFC 6209:
             Addition of the ARIA Cipher Suites to Transport Layer
             Security (TLS)";
      }
      enum TLS_ECDHE_ECDSA_WITH_ARIA_128_GCM_SHA256 {
        status deprecated;
        description
          "Enumeration for the
           'TLS_ECDHE_ECDSA_WITH_ARIA_128_GCM_SHA256' algorithm.";
        reference
          "RFC 6209:
             Addition of the ARIA Cipher Suites to Transport Layer
             Security (TLS)";
      }
      enum TLS_ECDHE_ECDSA_WITH_ARIA_256_GCM_SHA384 {
        status deprecated;
        description
          "Enumeration for the
           'TLS_ECDHE_ECDSA_WITH_ARIA_256_GCM_SHA384' algorithm.";
        reference
          "RFC 6209:
             Addition of the ARIA Cipher Suites to Transport Layer
             Security (TLS)";
      }
      enum TLS_ECDH_ECDSA_WITH_ARIA_128_GCM_SHA256 {
        status deprecated;
        description
          "Enumeration for the
           'TLS_ECDH_ECDSA_WITH_ARIA_128_GCM_SHA256' algorithm.";
        reference
          "RFC 6209:
             Addition of the ARIA Cipher Suites to Transport Layer
             Security (TLS)";
      }
      enum TLS_ECDH_ECDSA_WITH_ARIA_256_GCM_SHA384 {
        status deprecated;
        description
          "Enumeration for the
           'TLS_ECDH_ECDSA_WITH_ARIA_256_GCM_SHA384' algorithm.";
        reference
          "RFC 6209:
             Addition of the ARIA Cipher Suites to Transport Layer
             Security (TLS)";
      }
      enum TLS_ECDHE_RSA_WITH_ARIA_128_GCM_SHA256 {
        status deprecated;
        description
          "Enumeration for the
           'TLS_ECDHE_RSA_WITH_ARIA_128_GCM_SHA256' algorithm.";
        reference
          "RFC 6209:
             Addition of the ARIA Cipher Suites to Transport Layer
             Security (TLS)";
      }
      enum TLS_ECDHE_RSA_WITH_ARIA_256_GCM_SHA384 {
        status deprecated;
        description
          "Enumeration for the
           'TLS_ECDHE_RSA_WITH_ARIA_256_GCM_SHA384' algorithm.";
        reference
          "RFC 6209:
             Addition of the ARIA Cipher Suites to Transport Layer
             Security (TLS)";
      }
      enum TLS_ECDH_RSA_WITH_ARIA_128_GCM_SHA256 {
        status deprecated;
        description
          "Enumeration for the
           'TLS_ECDH_RSA_WITH_ARIA_128_GCM_SHA256' algorithm.";
        reference
          "RFC 6209:
             Addition of the ARIA Cipher Suites to Transport Layer
             Security (TLS)";
      }
      enum TLS_ECDH_RSA_WITH_ARIA_256_GCM_SHA384 {
        status deprecated;
        description
          "Enumeration for the
           'TLS_ECDH_RSA_WITH_ARIA_256_GCM_SHA384' algorithm.";
        reference
          "RFC 6209:
             Addition of the ARIA Cipher Suites to Transport Layer
             Security (TLS)";
      }
      enum TLS_PSK_WITH_ARIA_128_CBC_SHA256 {
        status deprecated;
        description
          "Enumeration for the 'TLS_PSK_WITH_ARIA_128_CBC_SHA256'
           algorithm.";
        reference
          "RFC 6209:
             Addition of the ARIA Cipher Suites to Transport Layer
             Security (TLS)";
      }
      enum TLS_PSK_WITH_ARIA_256_CBC_SHA384 {
        status deprecated;
        description
          "Enumeration for the 'TLS_PSK_WITH_ARIA_256_CBC_SHA384'
           algorithm.";
        reference
          "RFC 6209:
             Addition of the ARIA Cipher Suites to Transport Layer
             Security (TLS)";
      }
      enum TLS_DHE_PSK_WITH_ARIA_128_CBC_SHA256 {
        status deprecated;
        description
          "Enumeration for the 'TLS_DHE_PSK_WITH_ARIA_128_CBC_SHA256'
           algorithm.";
        reference
          "RFC 6209:
             Addition of the ARIA Cipher Suites to Transport Layer
             Security (TLS)";
      }
      enum TLS_DHE_PSK_WITH_ARIA_256_CBC_SHA384 {
        status deprecated;
        description
          "Enumeration for the 'TLS_DHE_PSK_WITH_ARIA_256_CBC_SHA384'
           algorithm.";
        reference
          "RFC 6209:
             Addition of the ARIA Cipher Suites to Transport Layer
             Security (TLS)";
      }
      enum TLS_RSA_PSK_WITH_ARIA_128_CBC_SHA256 {
        status deprecated;
        description
          "Enumeration for the 'TLS_RSA_PSK_WITH_ARIA_128_CBC_SHA256'
           algorithm.";
        reference
          "RFC 6209:
             Addition of the ARIA Cipher Suites to Transport Layer
             Security (TLS)";
      }
      enum TLS_RSA_PSK_WITH_ARIA_256_CBC_SHA384 {
        status deprecated;
        description
          "Enumeration for the 'TLS_RSA_PSK_WITH_ARIA_256_CBC_SHA384'
           algorithm.";
        reference
          "RFC 6209:
             Addition of the ARIA Cipher Suites to Transport Layer
             Security (TLS)";
      }
      enum TLS_PSK_WITH_ARIA_128_GCM_SHA256 {
        status deprecated;
        description
          "Enumeration for the 'TLS_PSK_WITH_ARIA_128_GCM_SHA256'
           algorithm.";
        reference
          "RFC 6209:
             Addition of the ARIA Cipher Suites to Transport Layer
             Security (TLS)";
      }
      enum TLS_PSK_WITH_ARIA_256_GCM_SHA384 {
        status deprecated;
        description
          "Enumeration for the 'TLS_PSK_WITH_ARIA_256_GCM_SHA384'
           algorithm.";
        reference
          "RFC 6209:
             Addition of the ARIA Cipher Suites to Transport Layer
             Security (TLS)";
      }
      enum TLS_DHE_PSK_WITH_ARIA_128_GCM_SHA256 {
        status deprecated;
        description
          "Enumeration for the 'TLS_DHE_PSK_WITH_ARIA_128_GCM_SHA256'
           algorithm.";
        reference
          "RFC 6209:
             Addition of the ARIA Cipher Suites to Transport Layer
             Security (TLS)";
      }
      enum TLS_DHE_PSK_WITH_ARIA_256_GCM_SHA384 {
        status deprecated;
        description
          "Enumeration for the 'TLS_DHE_PSK_WITH_ARIA_256_GCM_SHA384'
           algorithm.";
        reference
          "RFC 6209:
             Addition of the ARIA Cipher Suites to Transport Layer
             Security (TLS)";
      }
      enum TLS_RSA_PSK_WITH_ARIA_128_GCM_SHA256 {
        status deprecated;
        description
          "Enumeration for the 'TLS_RSA_PSK_WITH_ARIA_128_GCM_SHA256'
           algorithm.";
        reference
          "RFC 6209:
             Addition of the ARIA Cipher Suites to Transport Layer
             Security (TLS)";
      }
      enum TLS_RSA_PSK_WITH_ARIA_256_GCM_SHA384 {
        status deprecated;
        description
          "Enumeration for the 'TLS_RSA_PSK_WITH_ARIA_256_GCM_SHA384'
           algorithm.";
        reference
          "RFC 6209:
             Addition of the ARIA Cipher Suites to Transport Layer
             Security (TLS)";
      }
      enum TLS_ECDHE_PSK_WITH_ARIA_128_CBC_SHA256 {
        status deprecated;
        description
          "Enumeration for the
           'TLS_ECDHE_PSK_WITH_ARIA_128_CBC_SHA256' algorithm.";
        reference
          "RFC 6209:
             Addition of the ARIA Cipher Suites to Transport Layer
             Security (TLS)";
      }
      enum TLS_ECDHE_PSK_WITH_ARIA_256_CBC_SHA384 {
        status deprecated;
        description
          "Enumeration for the
           'TLS_ECDHE_PSK_WITH_ARIA_256_CBC_SHA384' algorithm.";
        reference
          "RFC 6209:
             Addition of the ARIA Cipher Suites to Transport Layer
             Security (TLS)";
      }
      enum TLS_ECDHE_ECDSA_WITH_CAMELLIA_128_CBC_SHA256 {
        status deprecated;
        description
          "Enumeration for the
           'TLS_ECDHE_ECDSA_WITH_CAMELLIA_128_CBC_SHA256'
           algorithm.";
        reference
          "RFC 6367:
             Addition of the Camellia Cipher Suites to Transport
             Layer Security (TLS)";
      }
      enum TLS_ECDHE_ECDSA_WITH_CAMELLIA_256_CBC_SHA384 {
        status deprecated;
        description
          "Enumeration for the
           'TLS_ECDHE_ECDSA_WITH_CAMELLIA_256_CBC_SHA384'
           algorithm.";
        reference
          "RFC 6367:
             Addition of the Camellia Cipher Suites to Transport
             Layer Security (TLS)";
      }
      enum TLS_ECDH_ECDSA_WITH_CAMELLIA_128_CBC_SHA256 {
        status deprecated;
        description
          "Enumeration for the
           'TLS_ECDH_ECDSA_WITH_CAMELLIA_128_CBC_SHA256' algorithm.";
        reference
          "RFC 6367:
             Addition of the Camellia Cipher Suites to Transport
             Layer Security (TLS)";
      }
      enum TLS_ECDH_ECDSA_WITH_CAMELLIA_256_CBC_SHA384 {
        status deprecated;
        description
          "Enumeration for the
           'TLS_ECDH_ECDSA_WITH_CAMELLIA_256_CBC_SHA384' algorithm.";
        reference
          "RFC 6367:
             Addition of the Camellia Cipher Suites to Transport
             Layer Security (TLS)";
      }
      enum TLS_ECDHE_RSA_WITH_CAMELLIA_128_CBC_SHA256 {
        status deprecated;
        description
          "Enumeration for the
           'TLS_ECDHE_RSA_WITH_CAMELLIA_128_CBC_SHA256' algorithm.";
        reference
          "RFC 6367:
             Addition of the Camellia Cipher Suites to Transport
             Layer Security (TLS)";
      }
      enum TLS_ECDHE_RSA_WITH_CAMELLIA_256_CBC_SHA384 {
        status deprecated;
        description
          "Enumeration for the
           'TLS_ECDHE_RSA_WITH_CAMELLIA_256_CBC_SHA384' algorithm.";
        reference
          "RFC 6367:
             Addition of the Camellia Cipher Suites to Transport
             Layer Security (TLS)";
      }
      enum TLS_ECDH_RSA_WITH_CAMELLIA_128_CBC_SHA256 {
        status deprecated;
        description
          "Enumeration for the
           'TLS_ECDH_RSA_WITH_CAMELLIA_128_CBC_SHA256' algorithm.";
        reference
          "RFC 6367:
             Addition of the Camellia Cipher Suites to Transport
             Layer Security (TLS)";
      }
      enum TLS_ECDH_RSA_WITH_CAMELLIA_256_CBC_SHA384 {
        status deprecated;
        description
          "Enumeration for the
           'TLS_ECDH_RSA_WITH_CAMELLIA_256_CBC_SHA384' algorithm.";
        reference
          "RFC 6367:
             Addition of the Camellia Cipher Suites to Transport
             Layer Security (TLS)";
      }
      enum TLS_RSA_WITH_CAMELLIA_128_GCM_SHA256 {
        status deprecated;
        description
          "Enumeration for the 'TLS_RSA_WITH_CAMELLIA_128_GCM_SHA256'
           algorithm.";
        reference
          "RFC 6367:
             Addition of the Camellia Cipher Suites to Transport
             Layer Security (TLS)";
      }
      enum TLS_RSA_WITH_CAMELLIA_256_GCM_SHA384 {
        status deprecated;
        description
          "Enumeration for the 'TLS_RSA_WITH_CAMELLIA_256_GCM_SHA384'
           algorithm.";
        reference
          "RFC 6367:
             Addition of the Camellia Cipher Suites to Transport
             Layer Security (TLS)";
      }
      enum TLS_DHE_RSA_WITH_CAMELLIA_128_GCM_SHA256 {
        status deprecated;
        description
          "Enumeration for the
           'TLS_DHE_RSA_WITH_CAMELLIA_128_GCM_SHA256' algorithm.";
        reference
          "RFC 6367:
             Addition of the Camellia Cipher Suites to Transport
             Layer Security (TLS)";
      }
      enum TLS_DHE_RSA_WITH_CAMELLIA_256_GCM_SHA384 {
        status deprecated;
        description
          "Enumeration for the
           'TLS_DHE_RSA_WITH_CAMELLIA_256_GCM_SHA384' algorithm.";
        reference
          "RFC 6367:
             Addition of the Camellia Cipher Suites to Transport
             Layer Security (TLS)";
      }
      enum TLS_DH_RSA_WITH_CAMELLIA_128_GCM_SHA256 {
        status deprecated;
        description
          "Enumeration for the
           'TLS_DH_RSA_WITH_CAMELLIA_128_GCM_SHA256' algorithm.";
        reference
          "RFC 6367:
             Addition of the Camellia Cipher Suites to Transport
             Layer Security (TLS)";
      }
      enum TLS_DH_RSA_WITH_CAMELLIA_256_GCM_SHA384 {
        status deprecated;
        description
          "Enumeration for the
           'TLS_DH_RSA_WITH_CAMELLIA_256_GCM_SHA384' algorithm.";
        reference
          "RFC 6367:
             Addition of the Camellia Cipher Suites to Transport
             Layer Security (TLS)";
      }
      enum TLS_DHE_DSS_WITH_CAMELLIA_128_GCM_SHA256 {
        status deprecated;
        description
          "Enumeration for the
           'TLS_DHE_DSS_WITH_CAMELLIA_128_GCM_SHA256' algorithm.";
        reference
          "RFC 6367:
             Addition of the Camellia Cipher Suites to Transport
             Layer Security (TLS)";
      }
      enum TLS_DHE_DSS_WITH_CAMELLIA_256_GCM_SHA384 {
        status deprecated;
        description
          "Enumeration for the
           'TLS_DHE_DSS_WITH_CAMELLIA_256_GCM_SHA384' algorithm.";
        reference
          "RFC 6367:
             Addition of the Camellia Cipher Suites to Transport
             Layer Security (TLS)";
      }
      enum TLS_DH_DSS_WITH_CAMELLIA_128_GCM_SHA256 {
        status deprecated;
        description
          "Enumeration for the
           'TLS_DH_DSS_WITH_CAMELLIA_128_GCM_SHA256' algorithm.";
        reference
          "RFC 6367:
             Addition of the Camellia Cipher Suites to Transport
             Layer Security (TLS)";
      }
      enum TLS_DH_DSS_WITH_CAMELLIA_256_GCM_SHA384 {
        status deprecated;
        description
          "Enumeration for the
           'TLS_DH_DSS_WITH_CAMELLIA_256_GCM_SHA384' algorithm.";
        reference
          "RFC 6367:
             Addition of the Camellia Cipher Suites to Transport
             Layer Security (TLS)";
      }
      enum TLS_DH_anon_WITH_CAMELLIA_128_GCM_SHA256 {
        status deprecated;
        description
          "Enumeration for the
           'TLS_DH_anon_WITH_CAMELLIA_128_GCM_SHA256' algorithm.";
        reference
          "RFC 6367:
             Addition of the Camellia Cipher Suites to Transport
             Layer Security (TLS)";
      }
      enum TLS_DH_anon_WITH_CAMELLIA_256_GCM_SHA384 {
        status deprecated;
        description
          "Enumeration for the
           'TLS_DH_anon_WITH_CAMELLIA_256_GCM_SHA384' algorithm.";
        reference
          "RFC 6367:
             Addition of the Camellia Cipher Suites to Transport
             Layer Security (TLS)";
      }
      enum TLS_ECDHE_ECDSA_WITH_CAMELLIA_128_GCM_SHA256 {
        status deprecated;
        description
          "Enumeration for the
           'TLS_ECDHE_ECDSA_WITH_CAMELLIA_128_GCM_SHA256'
           algorithm.";
        reference
          "RFC 6367:
             Addition of the Camellia Cipher Suites to Transport
             Layer Security (TLS)";
      }
      enum TLS_ECDHE_ECDSA_WITH_CAMELLIA_256_GCM_SHA384 {
        status deprecated;
        description
          "Enumeration for the
           'TLS_ECDHE_ECDSA_WITH_CAMELLIA_256_GCM_SHA384'
           algorithm.";
        reference
          "RFC 6367:
             Addition of the Camellia Cipher Suites to Transport
             Layer Security (TLS)";
      }
      enum TLS_ECDH_ECDSA_WITH_CAMELLIA_128_GCM_SHA256 {
        status deprecated;
        description
          "Enumeration for the
           'TLS_ECDH_ECDSA_WITH_CAMELLIA_128_GCM_SHA256' algorithm.";
        reference
          "RFC 6367:
             Addition of the Camellia Cipher Suites to Transport
             Layer Security (TLS)";
      }
      enum TLS_ECDH_ECDSA_WITH_CAMELLIA_256_GCM_SHA384 {
        status deprecated;
        description
          "Enumeration for the
           'TLS_ECDH_ECDSA_WITH_CAMELLIA_256_GCM_SHA384' algorithm.";
        reference
          "RFC 6367:
             Addition of the Camellia Cipher Suites to Transport
             Layer Security (TLS)";
      }
      enum TLS_ECDHE_RSA_WITH_CAMELLIA_128_GCM_SHA256 {
        status deprecated;
        description
          "Enumeration for the
           'TLS_ECDHE_RSA_WITH_CAMELLIA_128_GCM_SHA256' algorithm.";
        reference
          "RFC 6367:
             Addition of the Camellia Cipher Suites to Transport
             Layer Security (TLS)";
      }
      enum TLS_ECDHE_RSA_WITH_CAMELLIA_256_GCM_SHA384 {
        status deprecated;
        description
          "Enumeration for the
           'TLS_ECDHE_RSA_WITH_CAMELLIA_256_GCM_SHA384' algorithm.";
        reference
          "RFC 6367:
             Addition of the Camellia Cipher Suites to Transport
             Layer Security (TLS)";
      }
      enum TLS_ECDH_RSA_WITH_CAMELLIA_128_GCM_SHA256 {
        status deprecated;
        description
          "Enumeration for the
           'TLS_ECDH_RSA_WITH_CAMELLIA_128_GCM_SHA256' algorithm.";
        reference
          "RFC 6367:
             Addition of the Camellia Cipher Suites to Transport
             Layer Security (TLS)";
      }
      enum TLS_ECDH_RSA_WITH_CAMELLIA_256_GCM_SHA384 {
        status deprecated;
        description
          "Enumeration for the
           'TLS_ECDH_RSA_WITH_CAMELLIA_256_GCM_SHA384' algorithm.";
        reference
          "RFC 6367:
             Addition of the Camellia Cipher Suites to Transport
             Layer Security (TLS)";
      }
      enum TLS_PSK_WITH_CAMELLIA_128_GCM_SHA256 {
        status deprecated;
        description
          "Enumeration for the 'TLS_PSK_WITH_CAMELLIA_128_GCM_SHA256'
           algorithm.";
        reference
          "RFC 6367:
             Addition of the Camellia Cipher Suites to Transport
             Layer Security (TLS)";
      }
      enum TLS_PSK_WITH_CAMELLIA_256_GCM_SHA384 {
        status deprecated;
        description
          "Enumeration for the 'TLS_PSK_WITH_CAMELLIA_256_GCM_SHA384'
           algorithm.";
        reference
          "RFC 6367:
             Addition of the Camellia Cipher Suites to Transport
             Layer Security (TLS)";
      }
      enum TLS_DHE_PSK_WITH_CAMELLIA_128_GCM_SHA256 {
        status deprecated;
        description
          "Enumeration for the
           'TLS_DHE_PSK_WITH_CAMELLIA_128_GCM_SHA256' algorithm.";
        reference
          "RFC 6367:
             Addition of the Camellia Cipher Suites to Transport
             Layer Security (TLS)";
      }
      enum TLS_DHE_PSK_WITH_CAMELLIA_256_GCM_SHA384 {
        status deprecated;
        description
          "Enumeration for the
           'TLS_DHE_PSK_WITH_CAMELLIA_256_GCM_SHA384' algorithm.";
        reference
          "RFC 6367:
             Addition of the Camellia Cipher Suites to Transport
             Layer Security (TLS)";
      }
      enum TLS_RSA_PSK_WITH_CAMELLIA_128_GCM_SHA256 {
        status deprecated;
        description
          "Enumeration for the
           'TLS_RSA_PSK_WITH_CAMELLIA_128_GCM_SHA256' algorithm.";
        reference
          "RFC 6367:
             Addition of the Camellia Cipher Suites to Transport
             Layer Security (TLS)";
      }
      enum TLS_RSA_PSK_WITH_CAMELLIA_256_GCM_SHA384 {
        status deprecated;
        description
          "Enumeration for the
           'TLS_RSA_PSK_WITH_CAMELLIA_256_GCM_SHA384' algorithm.";
        reference
          "RFC 6367:
             Addition of the Camellia Cipher Suites to Transport
             Layer Security (TLS)";
      }
      enum TLS_PSK_WITH_CAMELLIA_128_CBC_SHA256 {
        status deprecated;
        description
          "Enumeration for the 'TLS_PSK_WITH_CAMELLIA_128_CBC_SHA256'
           algorithm.";
        reference
          "RFC 6367:
             Addition of the Camellia Cipher Suites to Transport
             Layer Security (TLS)";
      }
      enum TLS_PSK_WITH_CAMELLIA_256_CBC_SHA384 {
        status deprecated;
        description
          "Enumeration for the 'TLS_PSK_WITH_CAMELLIA_256_CBC_SHA384'
           algorithm.";
        reference
          "RFC 6367:
             Addition of the Camellia Cipher Suites to Transport
             Layer Security (TLS)";
      }
      enum TLS_DHE_PSK_WITH_CAMELLIA_128_CBC_SHA256 {
        status deprecated;
        description
          "Enumeration for the
           'TLS_DHE_PSK_WITH_CAMELLIA_128_CBC_SHA256' algorithm.";
        reference
          "RFC 6367:
             Addition of the Camellia Cipher Suites to Transport
             Layer Security (TLS)";
      }
      enum TLS_DHE_PSK_WITH_CAMELLIA_256_CBC_SHA384 {
        status deprecated;
        description
          "Enumeration for the
           'TLS_DHE_PSK_WITH_CAMELLIA_256_CBC_SHA384' algorithm.";
        reference
          "RFC 6367:
             Addition of the Camellia Cipher Suites to Transport
             Layer Security (TLS)";
      }
      enum TLS_RSA_PSK_WITH_CAMELLIA_128_CBC_SHA256 {
        status deprecated;
        description
          "Enumeration for the
           'TLS_RSA_PSK_WITH_CAMELLIA_128_CBC_SHA256' algorithm.";
        reference
          "RFC 6367:
             Addition of the Camellia Cipher Suites to Transport
             Layer Security (TLS)";
      }
      enum TLS_RSA_PSK_WITH_CAMELLIA_256_CBC_SHA384 {
        status deprecated;
        description
          "Enumeration for the
           'TLS_RSA_PSK_WITH_CAMELLIA_256_CBC_SHA384' algorithm.";
        reference
          "RFC 6367:
             Addition of the Camellia Cipher Suites to Transport
             Layer Security (TLS)";
      }
      enum TLS_ECDHE_PSK_WITH_CAMELLIA_128_CBC_SHA256 {
        status deprecated;
        description
          "Enumeration for the
           'TLS_ECDHE_PSK_WITH_CAMELLIA_128_CBC_SHA256' algorithm.";
        reference
          "RFC 6367:
             Addition of the Camellia Cipher Suites to Transport
             Layer Security (TLS)";
      }
      enum TLS_ECDHE_PSK_WITH_CAMELLIA_256_CBC_SHA384 {
        status deprecated;
        description
          "Enumeration for the
           'TLS_ECDHE_PSK_WITH_CAMELLIA_256_CBC_SHA384' algorithm.";
        reference
          "RFC 6367:
             Addition of the Camellia Cipher Suites to Transport
             Layer Security (TLS)";
      }
      enum TLS_RSA_WITH_AES_128_CCM {
        status deprecated;
        description
          "Enumeration for the 'TLS_RSA_WITH_AES_128_CCM'
           algorithm.";
        reference
          "RFC 6655:
             AES-CCM Cipher Suites for Transport Layer Security
             (TLS)";
      }
      enum TLS_RSA_WITH_AES_256_CCM {
        status deprecated;
        description
          "Enumeration for the 'TLS_RSA_WITH_AES_256_CCM'
           algorithm.";
        reference
          "RFC 6655:
             AES-CCM Cipher Suites for Transport Layer Security
             (TLS)";
      }
      enum TLS_DHE_RSA_WITH_AES_128_CCM {
        description
          "Enumeration for the 'TLS_DHE_RSA_WITH_AES_128_CCM'
           algorithm.";
        reference
          "RFC 6655:
             AES-CCM Cipher Suites for Transport Layer Security
             (TLS)";
      }
      enum TLS_DHE_RSA_WITH_AES_256_CCM {
        description
          "Enumeration for the 'TLS_DHE_RSA_WITH_AES_256_CCM'
           algorithm.";
        reference
          "RFC 6655:
             AES-CCM Cipher Suites for Transport Layer Security
             (TLS)";
      }
      enum TLS_RSA_WITH_AES_128_CCM_8 {
        status deprecated;
        description
          "Enumeration for the 'TLS_RSA_WITH_AES_128_CCM_8'
           algorithm.";
        reference
          "RFC 6655:
             AES-CCM Cipher Suites for Transport Layer Security
             (TLS)";
      }
      enum TLS_RSA_WITH_AES_256_CCM_8 {
        status deprecated;
        description
          "Enumeration for the 'TLS_RSA_WITH_AES_256_CCM_8'
           algorithm.";
        reference
          "RFC 6655:
             AES-CCM Cipher Suites for Transport Layer Security
             (TLS)";
      }
      enum TLS_DHE_RSA_WITH_AES_128_CCM_8 {
        status deprecated;
        description
          "Enumeration for the 'TLS_DHE_RSA_WITH_AES_128_CCM_8'
           algorithm.";
        reference
          "RFC 6655:
             AES-CCM Cipher Suites for Transport Layer Security
             (TLS)";
      }
      enum TLS_DHE_RSA_WITH_AES_256_CCM_8 {
        status deprecated;
        description
          "Enumeration for the 'TLS_DHE_RSA_WITH_AES_256_CCM_8'
           algorithm.";
        reference
          "RFC 6655:
             AES-CCM Cipher Suites for Transport Layer Security
             (TLS)";
      }
      enum TLS_PSK_WITH_AES_128_CCM {
        status deprecated;
        description
          "Enumeration for the 'TLS_PSK_WITH_AES_128_CCM'
           algorithm.";
        reference
          "RFC 6655:
             AES-CCM Cipher Suites for Transport Layer Security
             (TLS)";
      }
      enum TLS_PSK_WITH_AES_256_CCM {
        status deprecated;
        description
          "Enumeration for the 'TLS_PSK_WITH_AES_256_CCM'
           algorithm.";
        reference
          "RFC 6655:
             AES-CCM Cipher Suites for Transport Layer Security
             (TLS)";
      }
      enum TLS_DHE_PSK_WITH_AES_128_CCM {
        description
          "Enumeration for the 'TLS_DHE_PSK_WITH_AES_128_CCM'
           algorithm.";
        reference
          "RFC 6655:
             AES-CCM Cipher Suites for Transport Layer Security
             (TLS)";
      }
      enum TLS_DHE_PSK_WITH_AES_256_CCM {
        description
          "Enumeration for the 'TLS_DHE_PSK_WITH_AES_256_CCM'
           algorithm.";
        reference
          "RFC 6655:
             AES-CCM Cipher Suites for Transport Layer Security
             (TLS)";
      }
      enum TLS_PSK_WITH_AES_128_CCM_8 {
        status deprecated;
        description
          "Enumeration for the 'TLS_PSK_WITH_AES_128_CCM_8'
           algorithm.";
        reference
          "RFC 6655:
             AES-CCM Cipher Suites for Transport Layer Security
             (TLS)";
      }
      enum TLS_PSK_WITH_AES_256_CCM_8 {
        status deprecated;
        description
          "Enumeration for the 'TLS_PSK_WITH_AES_256_CCM_8'
           algorithm.";
        reference
          "RFC 6655:
             AES-CCM Cipher Suites for Transport Layer Security
             (TLS)";
      }
      enum TLS_PSK_DHE_WITH_AES_128_CCM_8 {
        status deprecated;
        description
          "Enumeration for the 'TLS_PSK_DHE_WITH_AES_128_CCM_8'
           algorithm.";
        reference
          "RFC 6655:
             AES-CCM Cipher Suites for Transport Layer Security
             (TLS)";
      }
      enum TLS_PSK_DHE_WITH_AES_256_CCM_8 {
        status deprecated;
        description
          "Enumeration for the 'TLS_PSK_DHE_WITH_AES_256_CCM_8'
           algorithm.";
        reference
          "RFC 6655:
             AES-CCM Cipher Suites for Transport Layer Security
             (TLS)";
      }
      enum TLS_ECDHE_ECDSA_WITH_AES_128_CCM {
        status deprecated;
        description
          "Enumeration for the 'TLS_ECDHE_ECDSA_WITH_AES_128_CCM'
           algorithm.";
        reference
          "RFC 7251:
             AES-CCM Elliptic Curve Cryptography (ECC) Cipher Suites
             for TLS";
      }
      enum TLS_ECDHE_ECDSA_WITH_AES_256_CCM {
        status deprecated;
        description
          "Enumeration for the 'TLS_ECDHE_ECDSA_WITH_AES_256_CCM'
           algorithm.";
        reference
          "RFC 7251:
             AES-CCM Elliptic Curve Cryptography (ECC) Cipher Suites
             for TLS";
      }
      enum TLS_ECDHE_ECDSA_WITH_AES_128_CCM_8 {
        status deprecated;
        description
          "Enumeration for the 'TLS_ECDHE_ECDSA_WITH_AES_128_CCM_8'
           algorithm.";
        reference
          "RFC 7251:
             AES-CCM Elliptic Curve Cryptography (ECC) Cipher Suites
             for TLS";
      }
      enum TLS_ECDHE_ECDSA_WITH_AES_256_CCM_8 {
        status deprecated;
        description
          "Enumeration for the 'TLS_ECDHE_ECDSA_WITH_AES_256_CCM_8'
           algorithm.";
        reference
          "RFC 7251:
             AES-CCM Elliptic Curve Cryptography (ECC) Cipher Suites
             for TLS";
      }
      enum TLS_ECCPWD_WITH_AES_128_GCM_SHA256 {
        status deprecated;
        description
          "Enumeration for the 'TLS_ECCPWD_WITH_AES_128_GCM_SHA256'
           algorithm.";
        reference
          "RFC 8492:
             Secure Password Ciphersuites for Transport Layer
             Security (TLS)";
      }
      enum TLS_ECCPWD_WITH_AES_256_GCM_SHA384 {
        status deprecated;
        description
          "Enumeration for the 'TLS_ECCPWD_WITH_AES_256_GCM_SHA384'
           algorithm.";
        reference
          "RFC 8492:
             Secure Password Ciphersuites for Transport Layer
             Security (TLS)";
      }
      enum TLS_ECCPWD_WITH_AES_128_CCM_SHA256 {
        status deprecated;
        description
          "Enumeration for the 'TLS_ECCPWD_WITH_AES_128_CCM_SHA256'
           algorithm.";
        reference
          "RFC 8492:
             Secure Password Ciphersuites for Transport Layer
             Security (TLS)";
      }
      enum TLS_ECCPWD_WITH_AES_256_CCM_SHA384 {
        status deprecated;
        description
          "Enumeration for the 'TLS_ECCPWD_WITH_AES_256_CCM_SHA384'
           algorithm.";
        reference
          "RFC 8492:
             Secure Password Ciphersuites for Transport Layer
             Security (TLS)";
      }
      enum TLS_SHA256_SHA256 {
        status deprecated;
        description
          "Enumeration for the 'TLS_SHA256_SHA256' algorithm.";
        reference
          "RFC 9150:
             TLS 1.3 Authentication and Integrity-Only Cipher
             Suites";
      }
      enum TLS_SHA384_SHA384 {
        status deprecated;
        description
          "Enumeration for the 'TLS_SHA384_SHA384' algorithm.";
        reference
          "RFC 9150:
             TLS 1.3 Authentication and Integrity-Only Cipher
             Suites";
      }
      enum TLS_GOSTR341112_256_WITH_KUZNYECHIK_CTR_OMAC {
        status deprecated;
        description
          "Enumeration for the
           'TLS_GOSTR341112_256_WITH_KUZNYECHIK_CTR_OMAC'
           algorithm.";
        reference
          "RFC 9189:
             GOST Cipher Suites for Transport Layer Security (TLS)
             Protocol Version 1.2";
      }
      enum TLS_GOSTR341112_256_WITH_MAGMA_CTR_OMAC {
        status deprecated;
        description
          "Enumeration for the
           'TLS_GOSTR341112_256_WITH_MAGMA_CTR_OMAC' algorithm.";
        reference
          "RFC 9189:
             GOST Cipher Suites for Transport Layer Security (TLS)
             Protocol Version 1.2";
      }
      enum TLS_GOSTR341112_256_WITH_28147_CNT_IMIT {
        status deprecated;
        description
          "Enumeration for the
           'TLS_GOSTR341112_256_WITH_28147_CNT_IMIT' algorithm.";
        reference
          "RFC 9189:
             GOST Cipher Suites for Transport Layer Security (TLS)
             Protocol Version 1.2";
      }
      enum TLS_GOSTR341112_256_WITH_KUZNYECHIK_MGM_L {
        status deprecated;
        description
          "Enumeration for the
           'TLS_GOSTR341112_256_WITH_KUZNYECHIK_MGM_L' algorithm.";
        reference
          "RFC 9367:
             GOST Cipher Suites for Transport Layer Security (TLS)
             Protocol Version 1.3";
      }
      enum TLS_GOSTR341112_256_WITH_MAGMA_MGM_L {
        status deprecated;
        description
          "Enumeration for the 'TLS_GOSTR341112_256_WITH_MAGMA_MGM_L'
           algorithm.";
        reference
          "RFC 9367:
             GOST Cipher Suites for Transport Layer Security (TLS)
             Protocol Version 1.3";
      }
      enum TLS_GOSTR341112_256_WITH_KUZNYECHIK_MGM_S {
        status deprecated;
        description
          "Enumeration for the
           'TLS_GOSTR341112_256_WITH_KUZNYECHIK_MGM_S' algorithm.";
        reference
          "RFC 9367:
             GOST Cipher Suites for Transport Layer Security (TLS)
             Protocol Version 1.3";
      }
      enum TLS_GOSTR341112_256_WITH_MAGMA_MGM_S {
        status deprecated;
        description
          "Enumeration for the 'TLS_GOSTR341112_256_WITH_MAGMA_MGM_S'
           algorithm.";
        reference
          "RFC 9367:
             GOST Cipher Suites for Transport Layer Security (TLS)
             Protocol Version 1.3";
      }
      enum TLS_ECDHE_RSA_WITH_CHACHA20_POLY1305_SHA256 {
        description
          "Enumeration for the
           'TLS_ECDHE_RSA_WITH_CHACHA20_POLY1305_SHA256' algorithm.";
        reference
          "RFC 7905:
             ChaCha20-Poly1305 Cipher Suites for Transport Layer
             Security (TLS)";
      }
      enum TLS_ECDHE_ECDSA_WITH_CHACHA20_POLY1305_SHA256 {
        description
          "Enumeration for the
           'TLS_ECDHE_ECDSA_WITH_CHACHA20_POLY1305_SHA256'
           algorithm.";
        reference
          "RFC 7905:
             ChaCha20-Poly1305 Cipher Suites for Transport Layer
             Security (TLS)";
      }
      enum TLS_DHE_RSA_WITH_CHACHA20_POLY1305_SHA256 {
        description
          "Enumeration for the
           'TLS_DHE_RSA_WITH_CHACHA20_POLY1305_SHA256' algorithm.";
        reference
          "RFC 7905:
             ChaCha20-Poly1305 Cipher Suites for Transport Layer
             Security (TLS)";
      }
      enum TLS_PSK_WITH_CHACHA20_POLY1305_SHA256 {
        status deprecated;
        description
          "Enumeration for the
           'TLS_PSK_WITH_CHACHA20_POLY1305_SHA256' algorithm.";
        reference
          "RFC 7905:
             ChaCha20-Poly1305 Cipher Suites for Transport Layer
             Security (TLS)";
      }
      enum TLS_ECDHE_PSK_WITH_CHACHA20_POLY1305_SHA256 {
        description
          "Enumeration for the
           'TLS_ECDHE_PSK_WITH_CHACHA20_POLY1305_SHA256' algorithm.";
        reference
          "RFC 7905:
             ChaCha20-Poly1305 Cipher Suites for Transport Layer
             Security (TLS)";
      }
      enum TLS_DHE_PSK_WITH_CHACHA20_POLY1305_SHA256 {
        description
          "Enumeration for the
           'TLS_DHE_PSK_WITH_CHACHA20_POLY1305_SHA256' algorithm.";
        reference
          "RFC 7905:
             ChaCha20-Poly1305 Cipher Suites for Transport Layer
             Security (TLS)";
      }
      enum TLS_RSA_PSK_WITH_CHACHA20_POLY1305_SHA256 {
        status deprecated;
        description
          "Enumeration for the
           'TLS_RSA_PSK_WITH_CHACHA20_POLY1305_SHA256' algorithm.";
        reference
          "RFC 7905:
             ChaCha20-Poly1305 Cipher Suites for Transport Layer
             Security (TLS)";
      }
      enum TLS_ECDHE_PSK_WITH_AES_128_GCM_SHA256 {
        description
          "Enumeration for the
           'TLS_ECDHE_PSK_WITH_AES_128_GCM_SHA256' algorithm.";
        reference
          "RFC 8442:
             ECDHE_PSK with AES-GCM and AES-CCM Cipher Suites for TLS
             1.2 and DTLS 1.2";
      }
      enum TLS_ECDHE_PSK_WITH_AES_256_GCM_SHA384 {
        description
          "Enumeration for the
           'TLS_ECDHE_PSK_WITH_AES_256_GCM_SHA384' algorithm.";
        reference
          "RFC 8442:
             ECDHE_PSK with AES-GCM and AES-CCM Cipher Suites for TLS
             1.2 and DTLS 1.2";
      }
      enum TLS_ECDHE_PSK_WITH_AES_128_CCM_8_SHA256 {
        status deprecated;
        description
          "Enumeration for the
           'TLS_ECDHE_PSK_WITH_AES_128_CCM_8_SHA256' algorithm.";
        reference
          "RFC 8442:
             ECDHE_PSK with AES-GCM and AES-CCM Cipher Suites for TLS
             1.2 and DTLS 1.2";
      }
      enum TLS_ECDHE_PSK_WITH_AES_128_CCM_SHA256 {
        description
          "Enumeration for the
           'TLS_ECDHE_PSK_WITH_AES_128_CCM_SHA256' algorithm.";
        reference
          "RFC 8442:
             ECDHE_PSK with AES-GCM and AES-CCM Cipher Suites for TLS
             1.2 and DTLS 1.2";
      }
    }
    description      "An enumeration for TLS SNAME algorithms.";  }

}
